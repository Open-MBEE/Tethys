// Hesperia: a fictional Venus orbiter and atmospheric descent probe. The mission is invented;
// the physics is not. CONVENTIONS.md governs every file in this directory.
package Hesperia {
    doc /* Hesperia is a Venus orbiter carrying the short-lived atmospheric descent probe
         * Kestrel. It launches on the Arcturus-5H, cruises for about four months, enters
         * Venus orbit by a chemical insertion burn, lowers its orbit by aerobraking, releases
         * Kestrel into the atmosphere while relaying its descent telemetry, and maps the
         * planet from a near-polar science orbit before disposal. Every element of the
         * mission — stakeholders, requirements, architecture, budgets, behaviour, analyses,
         * verification, risks, the as-built individual and its operations — lives in the
         * sibling packages of this model. */
}
