// Mission tier: the flight dictionary of the Argent tug — every command, telemetry point, event
// and packet the flight software and the ground system agree on, with the tables the monitors
// read and the time code the packets carry. GENERATED by scripts/gen-flight-dictionary.py; edit
// the generator, not this file. Everything here is fictional except the CCSDS Space Packet
// primary header layout (CCSDS 133.0-B-2). Standard libraries only.
package TethysFlightDictionary {
    private import ScalarValues::*;
    private import SequenceFunctions::*;
    private import ControlFunctions::*;
    private import NumericalFunctions::*;
    private import ISQ::*;
    private import SI::*;
    private import TethysTugStructure::*;
    private import TethysIcds::*;
    private import TethysOperations::*;
    private import TethysFdir::MonitorLimits;
    private import TethysFdir::FdirLevel;
    private import TethysFdir::cruiseLimits;
    private import TethysFlightSoftware::SoftwareEvent;
    private import TethysFlightSoftware::ParameterTable;

    // ---- vocabulary ----------------------------------------------------------------------
    enum def ApplicationName {
        doc /* The applications of the flight software backbone, one literal per application definition of TethysFlightSoftware, in the backbone's order. A telemetry point, event or packet names its source with one. */
        enum cdh;
        enum gnc;
        enum sepControl;
        enum powerManagement;
        enum thermalControl;
        enum telecom;
        enum inspectorHandling;
        enum captureControl;
        enum autonomy;
        enum fdir;
        enum modeManagement;
        enum parameterBootUpdate;
    }
    enum def CommandCriticality {
        doc /* How a command is treated by the ground and the on-board command service: routine commands need no confirmation, critical ones are two-step on the ground, hazardous ones also carry a confirmation key on board. */
        enum routine;
        enum critical;
        enum hazardous;
    }
    enum def EventSeverity {
        doc /* Severity of an on-board event: information, a warning the operators review, a fault the fault application handles, or a critical event that drives a mode change. */
        enum info;
        enum warning;
        enum fault;
        enum critical;
    }
    enum def TelemetryKind {
        doc /* Housekeeping points are downlinked in every pass at a fixed rate; engineering points are recorded and downlinked on request. */
        enum housekeeping;
        enum engineering;
    }
    enum def Opcode {
        doc /* The opcode enumeration: one literal per command, 344 in all, named by the command mnemonic. The numeric opcode of each is on the command. */
        enum CDH_NOOP;
        enum CDH_RESET_PROCESSOR;
        enum CDH_SELECT_PRIME_COMPUTER;
        enum CDH_SET_CLOCK;
        enum CDH_ADJUST_CLOCK;
        enum CDH_DUMP_MEMORY;
        enum CDH_LOAD_MEMORY;
        enum CDH_START_RECORDING;
        enum CDH_STOP_RECORDING;
        enum CDH_DOWNLINK_FILE;
        enum CDH_DELETE_FILE;
        enum CDH_SET_DOWNLINK_PRIORITY;
        enum CDH_SET_WATCHDOG_PERIOD;
        enum CDH_CLEAR_COUNTERS;
        enum CDH_SET_APP_RATE_CDH;
        enum CDH_SET_APP_RATE_GNC;
        enum CDH_SET_APP_RATE_SEP;
        enum CDH_SET_APP_RATE_EPS;
        enum CDH_SET_APP_RATE_THM;
        enum CDH_SET_APP_RATE_COM;
        enum CDH_SET_APP_RATE_INS;
        enum CDH_SET_APP_RATE_CAP;
        enum CDH_SET_APP_RATE_AUT;
        enum CDH_SET_APP_RATE_FDR;
        enum CDH_SET_APP_RATE_MOD;
        enum CDH_SET_APP_RATE_PBU;
        enum GNC_SET_ATTITUDE_TARGET;
        enum GNC_SET_RATE_TARGET;
        enum GNC_SLEW_TO;
        enum GNC_HOLD_ATTITUDE;
        enum GNC_SELECT_STAR_TRACKER;
        enum GNC_SELECT_IMU;
        enum GNC_DESATURATE_WHEELS;
        enum GNC_SET_WHEEL_SPEED;
        enum GNC_ENABLE_RCS_CONTROL;
        enum GNC_DISABLE_RCS_CONTROL;
        enum GNC_UPLOAD_EPHEMERIS;
        enum GNC_SET_GUIDANCE_MODE;
        enum GNC_START_TCM;
        enum GNC_ABORT_TCM;
        enum GNC_SET_POINTING_TOLERANCE;
        enum GNC_RESET_ESTIMATOR;
        enum GNC_RCS_THRUSTER_ENABLE_01;
        enum GNC_RCS_THRUSTER_DISABLE_01;
        enum GNC_RCS_THRUSTER_ENABLE_02;
        enum GNC_RCS_THRUSTER_DISABLE_02;
        enum GNC_RCS_THRUSTER_ENABLE_03;
        enum GNC_RCS_THRUSTER_DISABLE_03;
        enum GNC_RCS_THRUSTER_ENABLE_04;
        enum GNC_RCS_THRUSTER_DISABLE_04;
        enum GNC_RCS_THRUSTER_ENABLE_05;
        enum GNC_RCS_THRUSTER_DISABLE_05;
        enum GNC_RCS_THRUSTER_ENABLE_06;
        enum GNC_RCS_THRUSTER_DISABLE_06;
        enum GNC_RCS_THRUSTER_ENABLE_07;
        enum GNC_RCS_THRUSTER_DISABLE_07;
        enum GNC_RCS_THRUSTER_ENABLE_08;
        enum GNC_RCS_THRUSTER_DISABLE_08;
        enum GNC_WHEEL_ON_1;
        enum GNC_WHEEL_OFF_1;
        enum GNC_WHEEL_ON_2;
        enum GNC_WHEEL_OFF_2;
        enum GNC_WHEEL_ON_3;
        enum GNC_WHEEL_OFF_3;
        enum GNC_WHEEL_ON_4;
        enum GNC_WHEEL_OFF_4;
        enum SEP_START_THRUST_ARC;
        enum SEP_STOP_THRUST;
        enum SEP_SET_THROTTLE;
        enum SEP_SELECT_THRUSTER;
        enum SEP_PRIME_FEED;
        enum SEP_VENT_FEED;
        enum SEP_SET_FLOW_RATE;
        enum SEP_THRUSTER_RESTART;
        enum SEP_OPEN_LATCH_VALVE;
        enum SEP_CLOSE_LATCH_VALVE;
        enum SEP_GIMBAL_SET;
        enum SEP_GIMBAL_HOME;
        enum SEP_SET_DISCHARGE_LIMIT;
        enum SEP_TANK_HEATER_SETPOINT;
        enum SEP_PPU_ON_1;
        enum SEP_PPU_OFF_1;
        enum SEP_PPU_ON_2;
        enum SEP_PPU_OFF_2;
        enum SEP_PPU_ON_3;
        enum SEP_PPU_OFF_3;
        enum SEP_CATHODE_HEATER_ON_1;
        enum SEP_CATHODE_HEATER_OFF_1;
        enum SEP_CATHODE_HEATER_ON_2;
        enum SEP_CATHODE_HEATER_OFF_2;
        enum SEP_CATHODE_HEATER_ON_3;
        enum SEP_CATHODE_HEATER_OFF_3;
        enum EPS_SET_BATTERY_CHARGE_LIMIT;
        enum EPS_SET_LOAD_SHED_LEVEL;
        enum EPS_SELECT_BATTERY;
        enum EPS_SADA_SET_ANGLE;
        enum EPS_SADA_TRACK_SUN;
        enum EPS_SADA_HOLD;
        enum EPS_SET_BUS_VOLTAGE_LIMITS;
        enum EPS_BALANCE_CELLS;
        enum EPS_RESET_SWITCH_TRIPS;
        enum EPS_SET_ARRAY_STRING_MASK;
        enum EPS_SWITCH_ON_01;
        enum EPS_SWITCH_OFF_01;
        enum EPS_SWITCH_ON_02;
        enum EPS_SWITCH_OFF_02;
        enum EPS_SWITCH_ON_03;
        enum EPS_SWITCH_OFF_03;
        enum EPS_SWITCH_ON_04;
        enum EPS_SWITCH_OFF_04;
        enum EPS_SWITCH_ON_05;
        enum EPS_SWITCH_OFF_05;
        enum EPS_SWITCH_ON_06;
        enum EPS_SWITCH_OFF_06;
        enum EPS_SWITCH_ON_07;
        enum EPS_SWITCH_OFF_07;
        enum EPS_SWITCH_ON_08;
        enum EPS_SWITCH_OFF_08;
        enum EPS_SWITCH_ON_09;
        enum EPS_SWITCH_OFF_09;
        enum EPS_SWITCH_ON_10;
        enum EPS_SWITCH_OFF_10;
        enum EPS_SWITCH_ON_11;
        enum EPS_SWITCH_OFF_11;
        enum EPS_SWITCH_ON_12;
        enum EPS_SWITCH_OFF_12;
        enum EPS_SWITCH_ON_13;
        enum EPS_SWITCH_OFF_13;
        enum EPS_SWITCH_ON_14;
        enum EPS_SWITCH_OFF_14;
        enum EPS_SWITCH_ON_15;
        enum EPS_SWITCH_OFF_15;
        enum EPS_SWITCH_ON_16;
        enum EPS_SWITCH_OFF_16;
        enum EPS_SWITCH_ON_17;
        enum EPS_SWITCH_OFF_17;
        enum EPS_SWITCH_ON_18;
        enum EPS_SWITCH_OFF_18;
        enum EPS_SWITCH_ON_19;
        enum EPS_SWITCH_OFF_19;
        enum EPS_SWITCH_ON_20;
        enum EPS_SWITCH_OFF_20;
        enum EPS_SWITCH_ON_21;
        enum EPS_SWITCH_OFF_21;
        enum EPS_SWITCH_ON_22;
        enum EPS_SWITCH_OFF_22;
        enum EPS_SWITCH_ON_23;
        enum EPS_SWITCH_OFF_23;
        enum EPS_SWITCH_ON_24;
        enum EPS_SWITCH_OFF_24;
        enum THM_SET_CONTROL_MODE;
        enum THM_LOUVER_SET;
        enum THM_LOUVER_AUTO;
        enum THM_SET_SURVIVAL_SETPOINTS;
        enum THM_SET_DEADBAND;
        enum THM_ENABLE_ALL_HEATERS;
        enum THM_DISABLE_ALL_HEATERS;
        enum THM_SET_HEATER_POWER_CAP;
        enum THM_HEATER_ENABLE_01;
        enum THM_HEATER_DISABLE_01;
        enum THM_HEATER_ENABLE_02;
        enum THM_HEATER_DISABLE_02;
        enum THM_HEATER_ENABLE_03;
        enum THM_HEATER_DISABLE_03;
        enum THM_HEATER_ENABLE_04;
        enum THM_HEATER_DISABLE_04;
        enum THM_HEATER_ENABLE_05;
        enum THM_HEATER_DISABLE_05;
        enum THM_HEATER_ENABLE_06;
        enum THM_HEATER_DISABLE_06;
        enum THM_HEATER_ENABLE_07;
        enum THM_HEATER_DISABLE_07;
        enum THM_HEATER_ENABLE_08;
        enum THM_HEATER_DISABLE_08;
        enum THM_HEATER_ENABLE_09;
        enum THM_HEATER_DISABLE_09;
        enum THM_HEATER_ENABLE_10;
        enum THM_HEATER_DISABLE_10;
        enum THM_HEATER_ENABLE_11;
        enum THM_HEATER_DISABLE_11;
        enum THM_HEATER_ENABLE_12;
        enum THM_HEATER_DISABLE_12;
        enum THM_HEATER_ENABLE_13;
        enum THM_HEATER_DISABLE_13;
        enum THM_HEATER_ENABLE_14;
        enum THM_HEATER_DISABLE_14;
        enum THM_HEATER_ENABLE_15;
        enum THM_HEATER_DISABLE_15;
        enum THM_HEATER_ENABLE_16;
        enum THM_HEATER_DISABLE_16;
        enum THM_HEATER_SETPOINT_01;
        enum THM_HEATER_SETPOINT_02;
        enum THM_HEATER_SETPOINT_03;
        enum THM_HEATER_SETPOINT_04;
        enum THM_HEATER_SETPOINT_05;
        enum THM_HEATER_SETPOINT_06;
        enum THM_HEATER_SETPOINT_07;
        enum THM_HEATER_SETPOINT_08;
        enum THM_HEATER_SETPOINT_09;
        enum THM_HEATER_SETPOINT_10;
        enum THM_HEATER_SETPOINT_11;
        enum THM_HEATER_SETPOINT_12;
        enum THM_HEATER_SETPOINT_13;
        enum THM_HEATER_SETPOINT_14;
        enum THM_HEATER_SETPOINT_15;
        enum THM_HEATER_SETPOINT_16;
        enum COM_TRANSMITTER_ON;
        enum COM_TRANSMITTER_OFF;
        enum COM_SELECT_TRANSPONDER;
        enum COM_SELECT_ANTENNA;
        enum COM_SET_DOWNLINK_RATE;
        enum COM_SET_UPLINK_RATE;
        enum COM_RANGING_ON;
        enum COM_RANGING_OFF;
        enum COM_HGA_POINT;
        enum COM_HGA_TRACK_EARTH;
        enum COM_HGA_STOW;
        enum COM_SET_PASS_WINDOW;
        enum COM_SET_CODING;
        enum COM_SET_TRANSMIT_POWER;
        enum COM_DOWNLINK_RATE_PRESET_1;
        enum COM_DOWNLINK_RATE_PRESET_2;
        enum COM_DOWNLINK_RATE_PRESET_3;
        enum COM_DOWNLINK_RATE_PRESET_4;
        enum COM_DOWNLINK_RATE_PRESET_5;
        enum COM_DOWNLINK_RATE_PRESET_6;
        enum INS_ARM_RELEASE;
        enum INS_SAFE_RELEASE;
        enum INS_RELEASE_INSPECTOR;
        enum INS_FORWARD_COMMAND;
        enum INS_START_IMAGING_SESSION;
        enum INS_STOP_IMAGING_SESSION;
        enum INS_SET_IMAGE_COMPRESSION;
        enum INS_SELECT_RELAY_RATE;
        enum INS_STORE_IMAGE_SEGMENT;
        enum INS_DOWNLINK_IMAGE;
        enum INS_RETIRE_INSPECTOR;
        enum INS_SET_RELAY_WINDOW;
        enum INS_ENABLE_RELAY;
        enum INS_DISABLE_RELAY;
        enum CAP_ARM_CAPTURE;
        enum CAP_DISARM_CAPTURE;
        enum CAP_DEPLOY_BAG;
        enum CAP_CLOSE_BAG;
        enum CAP_CINCH_BAG;
        enum CAP_START_DESPIN;
        enum CAP_STOP_DESPIN;
        enum CAP_SET_DESPIN_TORQUE;
        enum CAP_LATCH_BODY;
        enum CAP_RELEASE_BODY;
        enum CAP_ABORT_CAPTURE;
        enum CAP_SET_APPROACH_RATE;
        enum CAP_ENABLE_PROXIMITY_SENSORS;
        enum CAP_DISABLE_PROXIMITY_SENSORS;
        enum CAP_SET_CONTACT_FORCE_LIMIT;
        enum CAP_SET_BODY_MASS_ESTIMATE;
        enum CAP_PETAL_OPEN_1;
        enum CAP_PETAL_CLOSE_1;
        enum CAP_PETAL_OPEN_2;
        enum CAP_PETAL_CLOSE_2;
        enum CAP_PETAL_OPEN_3;
        enum CAP_PETAL_CLOSE_3;
        enum CAP_PETAL_OPEN_4;
        enum CAP_PETAL_CLOSE_4;
        enum AUT_LOAD_SEQUENCE;
        enum AUT_START_SEQUENCE;
        enum AUT_STOP_SEQUENCE;
        enum AUT_PAUSE_SEQUENCE;
        enum AUT_RESUME_SEQUENCE;
        enum AUT_SET_SEQUENCE_PARAMETER;
        enum AUT_ENABLE_AUTONOMY;
        enum AUT_DISABLE_AUTONOMY;
        enum AUT_SET_RULE_ENABLE;
        enum AUT_CLEAR_RULE_HISTORY;
        enum AUT_SET_WAYPOINT;
        enum AUT_CLEAR_WAYPOINTS;
        enum AUT_SET_PLAN_HORIZON;
        enum AUT_ENGINE_ENABLE_1;
        enum AUT_ENGINE_DISABLE_1;
        enum AUT_ENGINE_ENABLE_2;
        enum AUT_ENGINE_DISABLE_2;
        enum AUT_ENGINE_ENABLE_3;
        enum AUT_ENGINE_DISABLE_3;
        enum AUT_ENGINE_ENABLE_4;
        enum AUT_ENGINE_DISABLE_4;
        enum FDR_ENABLE_MONITOR;
        enum FDR_DISABLE_MONITOR;
        enum FDR_SET_LIMIT;
        enum FDR_RESET_LIMIT;
        enum FDR_CLEAR_FAULT;
        enum FDR_ACKNOWLEDGE_FAULT;
        enum FDR_MASK_RESPONSE;
        enum FDR_UNMASK_RESPONSE;
        enum FDR_FORCE_SAFE_MODE;
        enum FDR_SET_COMMAND_LOSS_TIMER;
        enum FDR_RESET_COMMAND_LOSS_TIMER;
        enum FDR_ABORT_TO_RETREAT;
        enum FDR_SET_FLAMEOUT_RETRIES;
        enum FDR_SET_BATTERY_LOW_FRACTION;
        enum FDR_SET_IMPACT_PROBABILITY_LIMIT;
        enum FDR_SET_EXCLUSION_RADIUS;
        enum FDR_MONITOR_RESPONSE_01;
        enum FDR_MONITOR_RESPONSE_02;
        enum FDR_MONITOR_RESPONSE_03;
        enum FDR_MONITOR_RESPONSE_04;
        enum FDR_MONITOR_RESPONSE_05;
        enum FDR_MONITOR_RESPONSE_06;
        enum FDR_MONITOR_RESPONSE_07;
        enum FDR_MONITOR_RESPONSE_08;
        enum FDR_MONITOR_RESPONSE_09;
        enum FDR_MONITOR_RESPONSE_10;
        enum FDR_MONITOR_RESPONSE_11;
        enum FDR_MONITOR_RESPONSE_12;
        enum MOD_SET_MODE;
        enum MOD_CONFIRM_MODE;
        enum MOD_CANCEL_PENDING_MODE;
        enum MOD_LOAD_MODE_TABLE;
        enum MOD_ENABLE_AUTO_TRANSITION;
        enum MOD_DISABLE_AUTO_TRANSITION;
        enum MOD_HOLD_MODE;
        enum MOD_RESUME_MODE;
        enum MOD_SET_TRANSITION_TIMEOUT;
        enum PBU_LOAD_TABLE;
        enum PBU_DUMP_TABLE;
        enum PBU_ACTIVATE_TABLE;
        enum PBU_VERIFY_TABLE;
        enum PBU_SET_PARAMETER;
        enum PBU_GET_PARAMETER;
        enum PBU_START_BOOT_UPDATE;
        enum PBU_ABORT_BOOT_UPDATE;
        enum PBU_SELECT_BOOT_IMAGE;
        enum PBU_COMMIT_BOOT_IMAGE;
        enum PBU_TABLE_RESET_01;
        enum PBU_TABLE_RESET_02;
        enum PBU_TABLE_RESET_03;
        enum PBU_TABLE_RESET_04;
        enum PBU_TABLE_RESET_05;
        enum PBU_TABLE_RESET_06;
        enum PBU_TABLE_RESET_07;
        enum PBU_TABLE_RESET_08;
        enum PBU_TABLE_RESET_09;
        enum PBU_TABLE_RESET_10;
        enum PBU_TABLE_RESET_11;
        enum PBU_TABLE_RESET_12;
    }

    // ---- time code and packet headers ---------------------------------------------------
    attribute def TethysTimeCode {
        doc /* The Tethys time code carried in every packet secondary header: 32 bits of seconds and 16 bits of 1/65 536 s fractions since the mission epoch, a fictional segmented code in the style of CCSDS 301.0-B-4 CUC. */
        attribute epoch : String = "2030-01-01T00:00:00 TRT";
        attribute coarseWidth : Natural = 32;
        attribute fineWidth : Natural = 16;
        attribute fineResolution : DurationValue = 1.52587890625e-5 [s];
        attribute width : Natural = coarseWidth + fineWidth;
    }
    attribute def PrimaryHeaderLayout {
        doc /* The CCSDS Space Packet primary header, 48 bits: version, type, secondary header flag, application process id, sequence flags, sequence count and data length (CCSDS 133.0-B-2 §4.1.3). */
        attribute versionWidth : Natural = 3;
        attribute typeWidth : Natural = 1;
        attribute secondaryHeaderFlagWidth : Natural = 1;
        attribute apidWidth : Natural = 11;
        attribute sequenceFlagsWidth : Natural = 2;
        attribute sequenceCountWidth : Natural = 14;
        attribute dataLengthWidth : Natural = 16;
        attribute width : Natural = versionWidth + typeWidth + secondaryHeaderFlagWidth + apidWidth + sequenceFlagsWidth + sequenceCountWidth + dataLengthWidth;
    }
    attribute def PacketField {
        doc /* One field of a packet data field: its order, bit offset from the start of the packet, width in bits and the mnemonic of the telemetry point it carries. */
        attribute order : Natural;
        attribute offset : Natural;
        attribute width : Natural;
        attribute point : String;
    }

    // ---- dictionary row definitions -----------------------------------------------------
    attribute def CommandArgument {
        doc /* A command argument: its range and the width it is packed into. An argument is typed by this and by its ISQ quantity type. */
        attribute minimum : Real;
        attribute maximum : Real;
        attribute widthBits : Natural;
    }
    item def CommandDefinition :> Command {
        doc /* One command of the dictionary: opcode literal and number, mnemonic, owning application, the modes it is accepted in, its criticality and hazard flag, and its arguments. */
        attribute opcodeLiteral : Opcode;
        attribute opcodeNumber : Natural;
        attribute mnemonic : String;
        attribute application : ApplicationName;
        attribute allowedModes : TugMode[1..*];
        attribute criticality : CommandCriticality;
        attribute hazardous : Boolean;
        attribute argumentCount : Natural;
        attribute argumentBits : Natural;
        attribute :>> opcode = mnemonic;
    }
    item def TelemetryPointDefinition :> TelemetryPoint {
        doc /* One telemetry point of the dictionary: id, source application, kind, sample rate, packed width and unit symbol. The typed value and limits are on the per-quantity specialisations. */
        attribute pointId : Natural;
        attribute source : ApplicationName;
        attribute kind : TelemetryKind;
        attribute rate : FrequencyValue;
        attribute widthBits : Natural;
        attribute unitSymbol : String;
    }
    item def TemperaturePoint :> TelemetryPointDefinition {
        doc /* A temperature point: value and red/yellow limits typed as ThermodynamicTemperatureValue. */
        attribute value : ThermodynamicTemperatureValue;
        attribute redLow : ThermodynamicTemperatureValue;
        attribute yellowLow : ThermodynamicTemperatureValue;
        attribute yellowHigh : ThermodynamicTemperatureValue;
        attribute redHigh : ThermodynamicTemperatureValue;
        attribute :>> widthBits = 16;
        attribute :>> unitSymbol = "K";
        assert constraint limitsOrdered { redLow <= yellowLow and yellowLow <= yellowHigh and yellowHigh <= redHigh }
    }
    item def VoltagePoint :> TelemetryPointDefinition {
        doc /* A voltage point: value and red/yellow limits typed as ElectricPotentialValue. */
        attribute value : ElectricPotentialValue;
        attribute redLow : ElectricPotentialValue;
        attribute yellowLow : ElectricPotentialValue;
        attribute yellowHigh : ElectricPotentialValue;
        attribute redHigh : ElectricPotentialValue;
        attribute :>> widthBits = 16;
        attribute :>> unitSymbol = "V";
        assert constraint limitsOrdered { redLow <= yellowLow and yellowLow <= yellowHigh and yellowHigh <= redHigh }
    }
    item def CurrentPoint :> TelemetryPointDefinition {
        doc /* A current point: value and red/yellow limits typed as ElectricCurrentValue. */
        attribute value : ElectricCurrentValue;
        attribute redLow : ElectricCurrentValue;
        attribute yellowLow : ElectricCurrentValue;
        attribute yellowHigh : ElectricCurrentValue;
        attribute redHigh : ElectricCurrentValue;
        attribute :>> widthBits = 16;
        attribute :>> unitSymbol = "A";
        assert constraint limitsOrdered { redLow <= yellowLow and yellowLow <= yellowHigh and yellowHigh <= redHigh }
    }
    item def PowerPoint :> TelemetryPointDefinition {
        doc /* A power point: value and red/yellow limits typed as PowerValue. */
        attribute value : PowerValue;
        attribute redLow : PowerValue;
        attribute yellowLow : PowerValue;
        attribute yellowHigh : PowerValue;
        attribute redHigh : PowerValue;
        attribute :>> widthBits = 16;
        attribute :>> unitSymbol = "W";
        assert constraint limitsOrdered { redLow <= yellowLow and yellowLow <= yellowHigh and yellowHigh <= redHigh }
    }
    item def PressurePoint :> TelemetryPointDefinition {
        doc /* A pressure point: value and red/yellow limits typed as PressureValue. */
        attribute value : PressureValue;
        attribute redLow : PressureValue;
        attribute yellowLow : PressureValue;
        attribute yellowHigh : PressureValue;
        attribute redHigh : PressureValue;
        attribute :>> widthBits = 16;
        attribute :>> unitSymbol = "Pa";
        assert constraint limitsOrdered { redLow <= yellowLow and yellowLow <= yellowHigh and yellowHigh <= redHigh }
    }
    item def AnglePoint :> TelemetryPointDefinition {
        doc /* A angle point: value and red/yellow limits typed as AngularMeasureValue. */
        attribute value : AngularMeasureValue;
        attribute redLow : AngularMeasureValue;
        attribute yellowLow : AngularMeasureValue;
        attribute yellowHigh : AngularMeasureValue;
        attribute redHigh : AngularMeasureValue;
        attribute :>> widthBits = 32;
        attribute :>> unitSymbol = "rad";
        assert constraint limitsOrdered { redLow <= yellowLow and yellowLow <= yellowHigh and yellowHigh <= redHigh }
    }
    item def AngularRatePoint :> TelemetryPointDefinition {
        doc /* A rate point: value and red/yellow limits typed as AngularVelocityValue. */
        attribute value : AngularVelocityValue;
        attribute redLow : AngularVelocityValue;
        attribute yellowLow : AngularVelocityValue;
        attribute yellowHigh : AngularVelocityValue;
        attribute redHigh : AngularVelocityValue;
        attribute :>> widthBits = 32;
        attribute :>> unitSymbol = "rad/s";
        assert constraint limitsOrdered { redLow <= yellowLow and yellowLow <= yellowHigh and yellowHigh <= redHigh }
    }
    item def LengthPoint :> TelemetryPointDefinition {
        doc /* A length point: value and red/yellow limits typed as LengthValue. */
        attribute value : LengthValue;
        attribute redLow : LengthValue;
        attribute yellowLow : LengthValue;
        attribute yellowHigh : LengthValue;
        attribute redHigh : LengthValue;
        attribute :>> widthBits = 32;
        attribute :>> unitSymbol = "m";
        assert constraint limitsOrdered { redLow <= yellowLow and yellowLow <= yellowHigh and yellowHigh <= redHigh }
    }
    item def SpeedPoint :> TelemetryPointDefinition {
        doc /* A speed point: value and red/yellow limits typed as SpeedValue. */
        attribute value : SpeedValue;
        attribute redLow : SpeedValue;
        attribute yellowLow : SpeedValue;
        attribute yellowHigh : SpeedValue;
        attribute redHigh : SpeedValue;
        attribute :>> widthBits = 32;
        attribute :>> unitSymbol = "m/s";
        assert constraint limitsOrdered { redLow <= yellowLow and yellowLow <= yellowHigh and yellowHigh <= redHigh }
    }
    item def DurationPoint :> TelemetryPointDefinition {
        doc /* A duration point: value and red/yellow limits typed as DurationValue. */
        attribute value : DurationValue;
        attribute redLow : DurationValue;
        attribute yellowLow : DurationValue;
        attribute yellowHigh : DurationValue;
        attribute redHigh : DurationValue;
        attribute :>> widthBits = 32;
        attribute :>> unitSymbol = "s";
        assert constraint limitsOrdered { redLow <= yellowLow and yellowLow <= yellowHigh and yellowHigh <= redHigh }
    }
    item def MassPoint :> TelemetryPointDefinition {
        doc /* A mass point: value and red/yellow limits typed as MassValue. */
        attribute value : MassValue;
        attribute redLow : MassValue;
        attribute yellowLow : MassValue;
        attribute yellowHigh : MassValue;
        attribute redHigh : MassValue;
        attribute :>> widthBits = 32;
        attribute :>> unitSymbol = "kg";
        assert constraint limitsOrdered { redLow <= yellowLow and yellowLow <= yellowHigh and yellowHigh <= redHigh }
    }
    item def ForcePoint :> TelemetryPointDefinition {
        doc /* A force point: value and red/yellow limits typed as ForceValue. */
        attribute value : ForceValue;
        attribute redLow : ForceValue;
        attribute yellowLow : ForceValue;
        attribute yellowHigh : ForceValue;
        attribute redHigh : ForceValue;
        attribute :>> widthBits = 16;
        attribute :>> unitSymbol = "N";
        assert constraint limitsOrdered { redLow <= yellowLow and yellowLow <= yellowHigh and yellowHigh <= redHigh }
    }
    item def FractionPoint :> TelemetryPointDefinition {
        doc /* A fraction point: value and red/yellow limits typed as Real. */
        attribute value : Real;
        attribute redLow : Real;
        attribute yellowLow : Real;
        attribute yellowHigh : Real;
        attribute redHigh : Real;
        attribute :>> widthBits = 16;
        attribute :>> unitSymbol = "1";
        assert constraint limitsOrdered { redLow <= yellowLow and yellowLow <= yellowHigh and yellowHigh <= redHigh }
    }
    item def CountPoint :> TelemetryPointDefinition {
        doc /* A count point: value and red/yellow limits typed as Natural. */
        attribute value : Natural;
        attribute redLow : Natural;
        attribute yellowLow : Natural;
        attribute yellowHigh : Natural;
        attribute redHigh : Natural;
        attribute :>> widthBits = 32;
        attribute :>> unitSymbol = "1";
        assert constraint limitsOrdered { redLow <= yellowLow and yellowLow <= yellowHigh and yellowHigh <= redHigh }
    }
    item def StatusPoint :> TelemetryPointDefinition {
        doc /* A status point: value and red/yellow limits typed as Natural. */
        attribute value : Natural;
        attribute redLow : Natural;
        attribute yellowLow : Natural;
        attribute yellowHigh : Natural;
        attribute redHigh : Natural;
        attribute :>> widthBits = 8;
        attribute :>> unitSymbol = "1";
        assert constraint limitsOrdered { redLow <= yellowLow and yellowLow <= yellowHigh and yellowHigh <= redHigh }
    }
    item def EventDefinition :> SoftwareEvent {
        doc /* One event of the dictionary: id, mnemonic, source application, severity, the text the ground shows, and whether the fault application acts on it. */
        attribute eventId : Natural;
        attribute mnemonic : String;
        attribute source : ApplicationName;
        attribute severity : EventSeverity;
        attribute text : String;
        attribute fdirRelevant : Boolean;
    }
    item def PacketDefinition :> TelemetryPacket {
        doc /* One telemetry packet of the dictionary: its APID and class, source application, rate, header layout, ordered fields, and the length the field widths must sum to. */
        attribute packetId : Natural;
        attribute mnemonic : String;
        attribute apidClass : ApidClass;
        attribute source : ApplicationName;
        attribute rate : FrequencyValue;
        attribute primaryHeader : PrimaryHeaderLayout;
        attribute timeCode : TethysTimeCode;
        attribute headerBits : Natural = primaryHeader.width + timeCode.width;
        attribute fieldCount : Natural;
        attribute widths : Natural[*] nonunique;
        attribute offsets : Natural[*];
        attribute payloadBits : Natural = sum(widths);
        attribute lengthOctets : Natural;
        attribute :>> length = lengthOctets [B];
        attribute layoutConsistent : Boolean = headerBits + payloadBits == lengthOctets * 8 and size(widths) == fieldCount
            and last(offsets) + last(widths) == lengthOctets * 8;
    }
    attribute def ParameterRow {
        doc /* One row of a parameter table: id, name, owning application, flight value, range and unit symbol. */
        attribute parameterId : Natural;
        attribute name : String;
        attribute owner : ApplicationName;
        attribute value : Real;
        attribute minimum : Real;
        attribute maximum : Real;
        attribute unitSymbol : String;
        attribute inRange : Boolean = minimum <= value and value <= maximum;
    }
    item def FlightParameterTable :> ParameterTable {
        doc /* A parameter table of one application: its rows, loaded and activated by the table service. */
        attribute owner : ApplicationName;
        attribute rows : ParameterRow[*];
        attribute rowCount : Natural = SequenceFunctions::size(rows);
        attribute :>> size = rowCount * 16 [B];
        attribute allInRange : Boolean = rows->forAll { in r : ParameterRow; r.inRange };
    }
    attribute def FdirLimitTable {
        doc /* The limit table the fault supervisor's monitors read: one typed row per monitor threshold, named as the threshold is named in the supervisor's limit set. */
        attribute tableId : Natural;
        attribute commandLossTimeout : DurationValue;
        attribute thrusterRestartDelay : DurationValue;
        attribute maximumFlameoutRetries : Natural;
        attribute batteryLowFraction : Real;
        attribute earthExclusionRadius : LengthValue;
        attribute maximumImpactProbability : Real;
        attribute rowCount : Natural = 6;
    }

    // ---- command dictionary: 344 commands ----------------------------------------
    item cdhNoop : CommandDefinition {
        doc /* No operation; exercises the command path and increments the accept counter. */
        :>> opcodeLiteral = Opcode::CDH_NOOP; :>> opcodeNumber = 257; :>> mnemonic = "CDH_NOOP";
        :>> application = ApplicationName::cdh; :>> apidClass = ApidClass::housekeeping; :>> apid = 960;
        :>> allowedModes = allFlightModes; :>> criticality = CommandCriticality::routine; :>> hazardous = false;
        :>> argumentCount = 0; :>> argumentBits = 0;
    }
    item cdhResetProcessor : CommandDefinition {
        doc /* Warm-reset the flight computer; all applications restart from their tables. */
        :>> opcodeLiteral = Opcode::CDH_RESET_PROCESSOR; :>> opcodeNumber = 258; :>> mnemonic = "CDH_RESET_PROCESSOR";
        :>> application = ApplicationName::cdh; :>> apidClass = ApidClass::housekeeping; :>> apid = 960;
        :>> allowedModes = (TugMode::earlyOperations, TugMode::coast, TugMode::droHold, TugMode::safe); :>> criticality = CommandCriticality::critical; :>> hazardous = true;
        :>> argumentCount = 1; :>> argumentBits = 16;
        attribute confirmKey : Natural, CommandArgument { :>> minimum = 0.0; :>> maximum = 65535.0; :>> widthBits = 16; }
    }
    item cdhSelectPrimeComputer : CommandDefinition {
        doc /* Make the named computer prime and the other hot spare. */
        :>> opcodeLiteral = Opcode::CDH_SELECT_PRIME_COMPUTER; :>> opcodeNumber = 259; :>> mnemonic = "CDH_SELECT_PRIME_COMPUTER";
        :>> application = ApplicationName::cdh; :>> apidClass = ApidClass::housekeeping; :>> apid = 960;
        :>> allowedModes = allFlightModes; :>> criticality = CommandCriticality::critical; :>> hazardous = false;
        :>> argumentCount = 1; :>> argumentBits = 8;
        attribute computer : Natural, CommandArgument { :>> minimum = 0.0; :>> maximum = 1.0; :>> widthBits = 8; }
    }
    item cdhSetClock : CommandDefinition {
        doc /* Set the spacecraft clock coarse and fine fields. */
        :>> opcodeLiteral = Opcode::CDH_SET_CLOCK; :>> opcodeNumber = 260; :>> mnemonic = "CDH_SET_CLOCK";
        :>> application = ApplicationName::cdh; :>> apidClass = ApidClass::housekeeping; :>> apid = 960;
        :>> allowedModes = allFlightModes; :>> criticality = CommandCriticality::critical; :>> hazardous = false;
        :>> argumentCount = 2; :>> argumentBits = 48;
        attribute coarseTime : Natural, CommandArgument { :>> minimum = 0.0; :>> maximum = 4294967295.0; :>> widthBits = 32; }
        attribute fineTime : Natural, CommandArgument { :>> minimum = 0.0; :>> maximum = 65535.0; :>> widthBits = 16; }
    }
    item cdhAdjustClock : CommandDefinition {
        doc /* Slew the spacecraft clock by a signed correction applied over the next pass. */
        :>> opcodeLiteral = Opcode::CDH_ADJUST_CLOCK; :>> opcodeNumber = 261; :>> mnemonic = "CDH_ADJUST_CLOCK";
        :>> application = ApplicationName::cdh; :>> apidClass = ApidClass::housekeeping; :>> apid = 960;
        :>> allowedModes = allFlightModes; :>> criticality = CommandCriticality::routine; :>> hazardous = false;
        :>> argumentCount = 2; :>> argumentBits = 64;
        attribute correction : DurationValue, CommandArgument { :>> minimum = -10.0; :>> maximum = 10.0; :>> widthBits = 32; }
        attribute slewPeriod : DurationValue, CommandArgument { :>> minimum = 1.0; :>> maximum = 86400.0; :>> widthBits = 32; }
    }
    item cdhDumpMemory : CommandDefinition {
        doc /* Downlink a memory region of the given address and length. */
        :>> opcodeLiteral = Opcode::CDH_DUMP_MEMORY; :>> opcodeNumber = 262; :>> mnemonic = "CDH_DUMP_MEMORY";
        :>> application = ApplicationName::cdh; :>> apidClass = ApidClass::housekeeping; :>> apid = 960;
        :>> allowedModes = allFlightModes; :>> criticality = CommandCriticality::routine; :>> hazardous = false;
        :>> argumentCount = 2; :>> argumentBits = 64;
        attribute address : Natural, CommandArgument { :>> minimum = 0.0; :>> maximum = 4294967295.0; :>> widthBits = 32; }
        attribute byteCount : Natural, CommandArgument { :>> minimum = 1.0; :>> maximum = 1048576.0; :>> widthBits = 32; }
    }
    item cdhLoadMemory : CommandDefinition {
        doc /* Write a memory region; the image follows in the data field. */
        :>> opcodeLiteral = Opcode::CDH_LOAD_MEMORY; :>> opcodeNumber = 263; :>> mnemonic = "CDH_LOAD_MEMORY";
        :>> application = ApplicationName::cdh; :>> apidClass = ApidClass::housekeeping; :>> apid = 960;
        :>> allowedModes = (TugMode::earlyOperations, TugMode::coast, TugMode::droHold, TugMode::safe); :>> criticality = CommandCriticality::critical; :>> hazardous = true;
        :>> argumentCount = 3; :>> argumentBits = 96;
        attribute address : Natural, CommandArgument { :>> minimum = 0.0; :>> maximum = 4294967295.0; :>> widthBits = 32; }
        attribute byteCount : Natural, CommandArgument { :>> minimum = 1.0; :>> maximum = 65536.0; :>> widthBits = 32; }
        attribute checksum : Natural, CommandArgument { :>> minimum = 0.0; :>> maximum = 4294967295.0; :>> widthBits = 32; }
    }
    item cdhStartRecording : CommandDefinition {
        doc /* Start recording the named telemetry packet class to the recorder. */
        :>> opcodeLiteral = Opcode::CDH_START_RECORDING; :>> opcodeNumber = 264; :>> mnemonic = "CDH_START_RECORDING";
        :>> application = ApplicationName::cdh; :>> apidClass = ApidClass::housekeeping; :>> apid = 960;
        :>> allowedModes = allFlightModes; :>> criticality = CommandCriticality::routine; :>> hazardous = false;
        :>> argumentCount = 1; :>> argumentBits = 8;
        attribute apidClassCode : Natural, CommandArgument { :>> minimum = 0.0; :>> maximum = 5.0; :>> widthBits = 8; }
    }
    item cdhStopRecording : CommandDefinition {
        doc /* Stop recording the named telemetry packet class. */
        :>> opcodeLiteral = Opcode::CDH_STOP_RECORDING; :>> opcodeNumber = 265; :>> mnemonic = "CDH_STOP_RECORDING";
        :>> application = ApplicationName::cdh; :>> apidClass = ApidClass::housekeeping; :>> apid = 960;
        :>> allowedModes = allFlightModes; :>> criticality = CommandCriticality::routine; :>> hazardous = false;
        :>> argumentCount = 1; :>> argumentBits = 8;
        attribute apidClassCode : Natural, CommandArgument { :>> minimum = 0.0; :>> maximum = 5.0; :>> widthBits = 8; }
    }
    item cdhDownlinkFile : CommandDefinition {
        doc /* Queue a recorder file for downlink at the given priority. */
        :>> opcodeLiteral = Opcode::CDH_DOWNLINK_FILE; :>> opcodeNumber = 266; :>> mnemonic = "CDH_DOWNLINK_FILE";
        :>> application = ApplicationName::cdh; :>> apidClass = ApidClass::housekeeping; :>> apid = 960;
        :>> allowedModes = allFlightModes; :>> criticality = CommandCriticality::routine; :>> hazardous = false;
        :>> argumentCount = 2; :>> argumentBits = 40;
        attribute fileId : Natural, CommandArgument { :>> minimum = 0.0; :>> maximum = 1048575.0; :>> widthBits = 32; }
        attribute priority : Natural, CommandArgument { :>> minimum = 0.0; :>> maximum = 7.0; :>> widthBits = 8; }
    }
    item cdhDeleteFile : CommandDefinition {
        doc /* Delete a recorder file after its downlink is confirmed. */
        :>> opcodeLiteral = Opcode::CDH_DELETE_FILE; :>> opcodeNumber = 267; :>> mnemonic = "CDH_DELETE_FILE";
        :>> application = ApplicationName::cdh; :>> apidClass = ApidClass::housekeeping; :>> apid = 960;
        :>> allowedModes = allFlightModes; :>> criticality = CommandCriticality::critical; :>> hazardous = false;
        :>> argumentCount = 1; :>> argumentBits = 32;
        attribute fileId : Natural, CommandArgument { :>> minimum = 0.0; :>> maximum = 1048575.0; :>> widthBits = 32; }
    }
    item cdhSetDownlinkPriority : CommandDefinition {
        doc /* Set the downlink priority of a telemetry packet class. */
        :>> opcodeLiteral = Opcode::CDH_SET_DOWNLINK_PRIORITY; :>> opcodeNumber = 268; :>> mnemonic = "CDH_SET_DOWNLINK_PRIORITY";
        :>> application = ApplicationName::cdh; :>> apidClass = ApidClass::housekeeping; :>> apid = 960;
        :>> allowedModes = allFlightModes; :>> criticality = CommandCriticality::routine; :>> hazardous = false;
        :>> argumentCount = 2; :>> argumentBits = 16;
        attribute apidClassCode : Natural, CommandArgument { :>> minimum = 0.0; :>> maximum = 5.0; :>> widthBits = 8; }
        attribute priority : Natural, CommandArgument { :>> minimum = 0.0; :>> maximum = 7.0; :>> widthBits = 8; }
    }
    item cdhSetWatchdogPeriod : CommandDefinition {
        doc /* Set the hardware watchdog kick period. */
        :>> opcodeLiteral = Opcode::CDH_SET_WATCHDOG_PERIOD; :>> opcodeNumber = 269; :>> mnemonic = "CDH_SET_WATCHDOG_PERIOD";
        :>> application = ApplicationName::cdh; :>> apidClass = ApidClass::housekeeping; :>> apid = 960;
        :>> allowedModes = (TugMode::earlyOperations, TugMode::coast, TugMode::droHold, TugMode::safe); :>> criticality = CommandCriticality::critical; :>> hazardous = false;
        :>> argumentCount = 1; :>> argumentBits = 32;
        attribute period : DurationValue, CommandArgument { :>> minimum = 0.1; :>> maximum = 30.0; :>> widthBits = 32; }
    }
    item cdhClearCounters : CommandDefinition {
        doc /* Zero the command accept and reject counters. */
        :>> opcodeLiteral = Opcode::CDH_CLEAR_COUNTERS; :>> opcodeNumber = 270; :>> mnemonic = "CDH_CLEAR_COUNTERS";
        :>> application = ApplicationName::cdh; :>> apidClass = ApidClass::housekeeping; :>> apid = 960;
        :>> allowedModes = allFlightModes; :>> criticality = CommandCriticality::routine; :>> hazardous = false;
        :>> argumentCount = 0; :>> argumentBits = 0;
    }
    item cdhSetAppRateCdh : CommandDefinition {
        doc /* Set the scheduling rate of the CDH application. */
        :>> opcodeLiteral = Opcode::CDH_SET_APP_RATE_CDH; :>> opcodeNumber = 271; :>> mnemonic = "CDH_SET_APP_RATE_CDH";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateGnc : CommandDefinition {
        doc /* Set the scheduling rate of the GNC application. */
        :>> opcodeLiteral = Opcode::CDH_SET_APP_RATE_GNC; :>> opcodeNumber = 272; :>> mnemonic = "CDH_SET_APP_RATE_GNC";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateSep : CommandDefinition {
        doc /* Set the scheduling rate of the SEP application. */
        :>> opcodeLiteral = Opcode::CDH_SET_APP_RATE_SEP; :>> opcodeNumber = 273; :>> mnemonic = "CDH_SET_APP_RATE_SEP";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateEps : CommandDefinition {
        doc /* Set the scheduling rate of the EPS application. */
        :>> opcodeLiteral = Opcode::CDH_SET_APP_RATE_EPS; :>> opcodeNumber = 274; :>> mnemonic = "CDH_SET_APP_RATE_EPS";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateThm : CommandDefinition {
        doc /* Set the scheduling rate of the THM application. */
        :>> opcodeLiteral = Opcode::CDH_SET_APP_RATE_THM; :>> opcodeNumber = 275; :>> mnemonic = "CDH_SET_APP_RATE_THM";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateCom : CommandDefinition {
        doc /* Set the scheduling rate of the COM application. */
        :>> opcodeLiteral = Opcode::CDH_SET_APP_RATE_COM; :>> opcodeNumber = 276; :>> mnemonic = "CDH_SET_APP_RATE_COM";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateIns : CommandDefinition {
        doc /* Set the scheduling rate of the INS application. */
        :>> opcodeLiteral = Opcode::CDH_SET_APP_RATE_INS; :>> opcodeNumber = 277; :>> mnemonic = "CDH_SET_APP_RATE_INS";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateCap : CommandDefinition {
        doc /* Set the scheduling rate of the CAP application. */
        :>> opcodeLiteral = Opcode::CDH_SET_APP_RATE_CAP; :>> opcodeNumber = 278; :>> mnemonic = "CDH_SET_APP_RATE_CAP";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateAut : CommandDefinition {
        doc /* Set the scheduling rate of the AUT application. */
        :>> opcodeLiteral = Opcode::CDH_SET_APP_RATE_AUT; :>> opcodeNumber = 279; :>> mnemonic = "CDH_SET_APP_RATE_AUT";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateFdr : CommandDefinition {
        doc /* Set the scheduling rate of the FDR application. */
        :>> opcodeLiteral = Opcode::CDH_SET_APP_RATE_FDR; :>> opcodeNumber = 280; :>> mnemonic = "CDH_SET_APP_RATE_FDR";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRateMod : CommandDefinition {
        doc /* Set the scheduling rate of the MOD application. */
        :>> opcodeLiteral = Opcode::CDH_SET_APP_RATE_MOD; :>> opcodeNumber = 281; :>> mnemonic = "CDH_SET_APP_RATE_MOD";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item cdhSetAppRatePbu : CommandDefinition {
        doc /* Set the scheduling rate of the PBU application. */
        :>> opcodeLiteral = Opcode::CDH_SET_APP_RATE_PBU; :>> opcodeNumber = 282; :>> mnemonic = "CDH_SET_APP_RATE_PBU";
        :>> application = ApplicationName::cdh; :>> apidClass = ApidClass::housekeeping; :>> apid = 960;
        :>> allowedModes = allFlightModes; :>> criticality = CommandCriticality::critical; :>> hazardous = false;
        :>> argumentCount = 1; :>> argumentBits = 16;
        attribute rate : FrequencyValue, CommandArgument { :>> minimum = 0.1; :>> maximum = 100.0; :>> widthBits = 16; }
    }
    item gncSetAttitudeTarget : CommandDefinition {
        doc /* Command a target quaternion; the controller slews to it at the rate limit. */
        :>> opcodeLiteral = Opcode::GNC_SET_ATTITUDE_TARGET; :>> opcodeNumber = 513; :>> mnemonic = "GNC_SET_ATTITUDE_TARGET";
        :>> application = ApplicationName::gnc; :>> apidClass = ApidClass::guidance; :>> apid = 961;
        :>> allowedModes = (TugMode::earlyOperations, thrustingModes, coastingModes, proximityModes, TugMode::capture, TugMode::despin, TugMode::droHold); :>> criticality = CommandCriticality::critical; :>> hazardous = false;
        :>> argumentCount = 4; :>> argumentBits = 128;
        attribute q1 : Real, CommandArgument { :>> minimum = -1.0; :>> maximum = 1.0; :>> widthBits = 32; }
        attribute q2 : Real, CommandArgument { :>> minimum = -1.0; :>> maximum = 1.0; :>> widthBits = 32; }
        attribute q3 : Real, CommandArgument { :>> minimum = -1.0; :>> maximum = 1.0; :>> widthBits = 32; }
        attribute q4 : Real, CommandArgument { :>> minimum = -1.0; :>> maximum = 1.0; :>> widthBits = 32; }
    }
    item gncSetRateTarget : CommandDefinition {
        doc /* Command a body rate target. */
        :>> opcodeLiteral = Opcode::GNC_SET_RATE_TARGET; :>> opcodeNumber = 514; :>> mnemonic = "GNC_SET_RATE_TARGET";
        :>> application = ApplicationName::gnc; :>> apidClass = ApidClass::guidance; :>> apid = 961;
        :>> allowedModes = (TugMode::earlyOperations, thrustingModes, coastingModes, proximityModes, TugMode::capture, TugMode::despin, TugMode::droHold); :>> criticality = CommandCriticality::critical; :>> hazardous = false;
        :>> argumentCount = 3; :>> argumentBits = 96;
        attribute rateX : AngularVelocityValue, CommandArgument { :>> minimum = -0.05; :>> maximum = 0.05; :>> widthBits = 32; }
        attribute rateY : AngularVelocityValue, CommandArgument { :>> minimum = -0.05; :>> maximum = 0.05; :>> widthBits = 32; }
        attribute rateZ : AngularVelocityValue, CommandArgument { :>> minimum = -0.05; :>> maximum = 0.05; :>> widthBits = 32; }
    }
    item gncSlewTo : CommandDefinition {
        doc /* Slew about the given axis by the given angle. */
        :>> opcodeLiteral = Opcode::GNC_SLEW_TO; :>> opcodeNumber = 515; :>> mnemonic = "GNC_SLEW_TO";
        :>> application = ApplicationName::gnc; :>> apidClass = ApidClass::guidance; :>> apid = 961;
        :>> allowedModes = (TugMode::earlyOperations, thrustingModes, coastingModes, proximityModes, TugMode::capture, TugMode::despin, TugMode::droHold); :>> criticality = CommandCriticality::critical; :>> hazardous = false;
        :>> argumentCount = 3; :>> argumentBits = 72;
        attribute axis : Natural, CommandArgument { :>> minimum = 0.0; :>> maximum = 2.0; :>> widthBits = 8; }
        attribute angle : AngularMeasureValue, CommandArgument { :>> minimum = -3.14159; :>> maximum = 3.14159; :>> widthBits = 32; }
        attribute slewRate : AngularVelocityValue, CommandArgument { :>> minimum = 0.0001; :>> maximum = 0.02; :>> widthBits = 32; }
    }
    item gncHoldAttitude : CommandDefinition {
        doc /* Hold the current attitude inertially. */
        :>> opcodeLiteral = Opcode::GNC_HOLD_ATTITUDE; :>> opcodeNumber = 516; :>> mnemonic = "GNC_HOLD_ATTITUDE";
        :>> application = ApplicationName::gnc; :>> apidClass = ApidClass::guidance; :>> apid = 961;
        :>> allowedModes = (TugMode::earlyOperations, thrustingModes, coastingModes, proximityModes, TugMode::capture, TugMode::despin, TugMode::droHold); :>> criticality = CommandCriticality::routine; :>> hazardous = false;
        :>> argumentCount = 0; :>> argumentBits = 0;
    }
    item gncSelectStarTracker : CommandDefinition {
        doc /* Select the star tracker used by the estimator. */
        :>> opcodeLiteral = Opcode::GNC_SELECT_STAR_TRACKER; :>> opcodeNumber = 517; :>> mnemonic = "GNC_SELECT_STAR_TRACKER";
        :>> application = ApplicationName::gnc; :>> apidClass = ApidClass::guidance; :>> apid = 961;
        :>> allowedModes = allFlightModes; :>> criticality = CommandCriticality::critical; :>> hazardous = false;
        :>> argumentCount = 1; :>> argumentBits = 8;
        attribute tracker : Natural, CommandArgument { :>> minimum = 0.0; :>> maximum = 1.0; :>> widthBits = 8; }
    }
    item gncSelectImu : CommandDefinition {
        doc /* Select the inertial measurement unit used by the estimator. */
        :>> opcodeLiteral = Opcode::GNC_SELECT_IMU; :>> opcodeNumber = 518; :>> mnemonic = "GNC_SELECT_IMU";
        :>> application = ApplicationName::gnc; :>> apidClass = ApidClass::guidance; :>> apid = 961;
        :>> allowedModes = allFlightModes; :>> criticality = CommandCriticality::critical; :>> hazardous = false;
        :>> argumentCount = 1; :>> argumentBits = 8;
        attribute imu : Natural, CommandArgument { :>> minimum = 0.0; :>> maximum = 1.0; :>> widthBits = 8; }
    }
    item gncDesaturateWheels : CommandDefinition {
        doc /* Dump wheel momentum with the reaction control thrusters. */
        :>> opcodeLiteral = Opcode::GNC_DESATURATE_WHEELS; :>> opcodeNumber = 519; :>> mnemonic = "GNC_DESATURATE_WHEELS";
        :>> application = ApplicationName::gnc; :>> apidClass = ApidClass::guidance; :>> apid = 961;
        :>> allowedModes = (TugMode::earlyOperations, thrustingModes, coastingModes, proximityModes, TugMode::capture, TugMode::despin, TugMode::droHold); :>> criticality = CommandCriticality::critical; :>> hazardous = true;
        :>> argumentCount = 1; :>> argumentBits = 16;
        attribute targetMomentumFraction : Real, CommandArgument { :>> minimum = 0.0; :>> maximum = 0.5; :>> widthBits = 16; }
    }
    item gncSetWheelSpeed : CommandDefinition {
        doc /* Command a wheel to a speed; for ground testing and bias management. */
        :>> opcodeLiteral = Opcode::GNC_SET_WHEEL_SPEED; :>> opcodeNumber = 520; :>> mnemonic = "GNC_SET_WHEEL_SPEED";
        :>> application = ApplicationName::gnc; :>> apidClass = ApidClass::guidance; :>> apid = 961;
        :>> allowedModes = (TugMode::earlyOperations, TugMode::coast, TugMode::droHold, TugMode::safe); :>> criticality = CommandCriticality::critical; :>> hazardous = false;
        :>> argumentCount = 2; :>> argumentBits = 40;
        attribute wheel : Natural, CommandArgument { :>> minimum = 0.0; :>> maximum = 3.0; :>> widthBits = 8; }
        attribute speed : AngularVelocityValue, CommandArgument { :>> minimum = -628.3; :>> maximum = 628.3; :>> widthBits = 32; }
    }
    item gncEnableRcsControl : CommandDefinition {
        doc /* Allow the controller to fire reaction control thrusters. */
        :>> opcodeLiteral = Opcode::GNC_ENABLE_RCS_CONTROL; :>> opcodeNumber = 521; :>> mnemonic = "GNC_ENABLE_RCS_CONTROL";
        :>> application = ApplicationName::gnc; :>> apidClass = ApidClass::guidance; :>> apid = 961;
        :>> allowedModes = (TugMode::earlyOperations, thrustingModes, coastingModes, proximityModes, TugMode::capture, TugMode::despin, TugMode::droHold); :>> criticality = CommandCriticality::critical; :>> hazardous = true;
        :>> argumentCount = 0; :>> argumentBits = 0;
    }
    item gncDisableRcsControl : CommandDefinition {
        doc /* Inhibit all reaction control thruster firing. */
        :>> opcodeLiteral = Opcode::GNC_DISABLE_RCS_CONTROL; :>> opcodeNumber = 522; :>> mnemonic = "GNC_DISABLE_RCS_CONTROL";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncUploadEphemeris : CommandDefinition {
        doc /* Load an ephemeris block for the tug, the Earth, the Moon or the target. */
        :>> opcodeLiteral = Opcode::GNC_UPLOAD_EPHEMERIS; :>> opcodeNumber = 523; :>> mnemonic = "GNC_UPLOAD_EPHEMERIS";
        :>> application = ApplicationName::gnc; :>> apidClass = ApidClass::guidance; :>> apid = 961;
        :>> allowedModes = allFlightModes; :>> criticality = CommandCriticality::routine; :>> hazardous = false;
        :>> argumentCount = 3; :>> argumentBits = 72;
        attribute body : Natural, CommandArgument { :>> minimum = 0.0; :>> maximum = 3.0; :>> widthBits = 8; }
        attribute epochCoarse : Natural, CommandArgument { :>> minimum = 0.0; :>> maximum = 4294967295.0; :>> widthBits = 32; }
        attribute validity : DurationValue, CommandArgument { :>> minimum = 3600.0; :>> maximum = 7776000.0; :>> widthBits = 32; }
    }
    item gncSetGuidanceMode : CommandDefinition {
        doc /* Select the guidance law: inertial hold, sun point, thrust vector or target track. */
        :>> opcodeLiteral = Opcode::GNC_SET_GUIDANCE_MODE; :>> opcodeNumber = 524; :>> mnemonic = "GNC_SET_GUIDANCE_MODE";
        :>> application = ApplicationName::gnc; :>> apidClass = ApidClass::guidance; :>> apid = 961;
        :>> allowedModes = (TugMode::earlyOperations, thrustingModes, coastingModes, proximityModes, TugMode::capture, TugMode::despin, TugMode::droHold); :>> criticality = CommandCriticality::critical; :>> hazardous = false;
        :>> argumentCount = 1; :>> argumentBits = 8;
        attribute law : Natural, CommandArgument { :>> minimum = 0.0; :>> maximum = 3.0; :>> widthBits = 8; }
    }
    item gncStartTcm : CommandDefinition {
        doc /* Execute a trajectory correction with the reaction control system. */
        :>> opcodeLiteral = Opcode::GNC_START_TCM; :>> opcodeNumber = 525; :>> mnemonic = "GNC_START_TCM";
        :>> application = ApplicationName::gnc; :>> apidClass = ApidClass::guidance; :>> apid = 961;
        :>> allowedModes = (TugMode::coast, TugMode::stackCoast, TugMode::approach); :>> criticality = CommandCriticality::critical; :>> hazardous = true;
        :>> argumentCount = 3; :>> argumentBits = 96;
        attribute deltaV : SpeedValue, CommandArgument { :>> minimum = 0.001; :>> maximum = 5.0; :>> widthBits = 32; }
        attribute direction : AngularMeasureValue, CommandArgument { :>> minimum = -3.14159; :>> maximum = 3.14159; :>> widthBits = 32; }
        attribute startDelay : DurationValue, CommandArgument { :>> minimum = 0.0; :>> maximum = 86400.0; :>> widthBits = 32; }
    }
    item gncAbortTcm : CommandDefinition {
        doc /* Stop a running trajectory correction immediately. */
        :>> opcodeLiteral = Opcode::GNC_ABORT_TCM; :>> opcodeNumber = 526; :>> mnemonic = "GNC_ABORT_TCM";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncSetPointingTolerance : CommandDefinition {
        doc /* Set the attitude error at which a slew is declared complete. */
        :>> opcodeLiteral = Opcode::GNC_SET_POINTING_TOLERANCE; :>> opcodeNumber = 527; :>> mnemonic = "GNC_SET_POINTING_TOLERANCE";
        :>> application = ApplicationName::gnc; :>> apidClass = ApidClass::guidance; :>> apid = 961;
        :>> allowedModes = allFlightModes; :>> criticality = CommandCriticality::routine; :>> hazardous = false;
        :>> argumentCount = 1; :>> argumentBits = 32;
        attribute tolerance : AngularMeasureValue, CommandArgument { :>> minimum = 0.0001; :>> maximum = 0.1; :>> widthBits = 32; }
    }
    item gncResetEstimator : CommandDefinition {
        doc /* Reinitialise the attitude estimator from the star tracker. */
        :>> opcodeLiteral = Opcode::GNC_RESET_ESTIMATOR; :>> opcodeNumber = 528; :>> mnemonic = "GNC_RESET_ESTIMATOR";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncRcsThrusterEnable01 : CommandDefinition {
        doc /* Enable reaction control thruster 1. */
        :>> opcodeLiteral = Opcode::GNC_RCS_THRUSTER_ENABLE_01; :>> opcodeNumber = 529; :>> mnemonic = "GNC_RCS_THRUSTER_ENABLE_01";
        :>> application = ApplicationName::gnc; :>> apidClass = ApidClass::guidance; :>> apid = 961;
        :>> allowedModes = allFlightModes; :>> criticality = CommandCriticality::critical; :>> hazardous = true;
        :>> argumentCount = 0; :>> argumentBits = 0;
    }
    item gncRcsThrusterDisable01 : CommandDefinition {
        doc /* Disable reaction control thruster 1. */
        :>> opcodeLiteral = Opcode::GNC_RCS_THRUSTER_DISABLE_01; :>> opcodeNumber = 530; :>> mnemonic = "GNC_RCS_THRUSTER_DISABLE_01";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncRcsThrusterEnable02 : CommandDefinition {
        doc /* Enable reaction control thruster 2. */
        :>> opcodeLiteral = Opcode::GNC_RCS_THRUSTER_ENABLE_02; :>> opcodeNumber = 531; :>> mnemonic = "GNC_RCS_THRUSTER_ENABLE_02";
        :>> application = ApplicationName::gnc; :>> apidClass = ApidClass::guidance; :>> apid = 961;
        :>> allowedModes = allFlightModes; :>> criticality = CommandCriticality::critical; :>> hazardous = true;
        :>> argumentCount = 0; :>> argumentBits = 0;
    }
    item gncRcsThrusterDisable02 : CommandDefinition {
        doc /* Disable reaction control thruster 2. */
        :>> opcodeLiteral = Opcode::GNC_RCS_THRUSTER_DISABLE_02; :>> opcodeNumber = 532; :>> mnemonic = "GNC_RCS_THRUSTER_DISABLE_02";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncRcsThrusterEnable03 : CommandDefinition {
        doc /* Enable reaction control thruster 3. */
        :>> opcodeLiteral = Opcode::GNC_RCS_THRUSTER_ENABLE_03; :>> opcodeNumber = 533; :>> mnemonic = "GNC_RCS_THRUSTER_ENABLE_03";
        :>> application = ApplicationName::gnc; :>> apidClass = ApidClass::guidance; :>> apid = 961;
        :>> allowedModes = allFlightModes; :>> criticality = CommandCriticality::critical; :>> hazardous = true;
        :>> argumentCount = 0; :>> argumentBits = 0;
    }
    item gncRcsThrusterDisable03 : CommandDefinition {
        doc /* Disable reaction control thruster 3. */
        :>> opcodeLiteral = Opcode::GNC_RCS_THRUSTER_DISABLE_03; :>> opcodeNumber = 534; :>> mnemonic = "GNC_RCS_THRUSTER_DISABLE_03";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncRcsThrusterEnable04 : CommandDefinition {
        doc /* Enable reaction control thruster 4. */
        :>> opcodeLiteral = Opcode::GNC_RCS_THRUSTER_ENABLE_04; :>> opcodeNumber = 535; :>> mnemonic = "GNC_RCS_THRUSTER_ENABLE_04";
        :>> application = ApplicationName::gnc; :>> apidClass = ApidClass::guidance; :>> apid = 961;
        :>> allowedModes = allFlightModes; :>> criticality = CommandCriticality::critical; :>> hazardous = true;
        :>> argumentCount = 0; :>> argumentBits = 0;
    }
    item gncRcsThrusterDisable04 : CommandDefinition {
        doc /* Disable reaction control thruster 4. */
        :>> opcodeLiteral = Opcode::GNC_RCS_THRUSTER_DISABLE_04; :>> opcodeNumber = 536; :>> mnemonic = "GNC_RCS_THRUSTER_DISABLE_04";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncRcsThrusterEnable05 : CommandDefinition {
        doc /* Enable reaction control thruster 5. */
        :>> opcodeLiteral = Opcode::GNC_RCS_THRUSTER_ENABLE_05; :>> opcodeNumber = 537; :>> mnemonic = "GNC_RCS_THRUSTER_ENABLE_05";
        :>> application = ApplicationName::gnc; :>> apidClass = ApidClass::guidance; :>> apid = 961;
        :>> allowedModes = allFlightModes; :>> criticality = CommandCriticality::critical; :>> hazardous = true;
        :>> argumentCount = 0; :>> argumentBits = 0;
    }
    item gncRcsThrusterDisable05 : CommandDefinition {
        doc /* Disable reaction control thruster 5. */
        :>> opcodeLiteral = Opcode::GNC_RCS_THRUSTER_DISABLE_05; :>> opcodeNumber = 538; :>> mnemonic = "GNC_RCS_THRUSTER_DISABLE_05";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncRcsThrusterEnable06 : CommandDefinition {
        doc /* Enable reaction control thruster 6. */
        :>> opcodeLiteral = Opcode::GNC_RCS_THRUSTER_ENABLE_06; :>> opcodeNumber = 539; :>> mnemonic = "GNC_RCS_THRUSTER_ENABLE_06";
        :>> application = ApplicationName::gnc; :>> apidClass = ApidClass::guidance; :>> apid = 961;
        :>> allowedModes = allFlightModes; :>> criticality = CommandCriticality::critical; :>> hazardous = true;
        :>> argumentCount = 0; :>> argumentBits = 0;
    }
    item gncRcsThrusterDisable06 : CommandDefinition {
        doc /* Disable reaction control thruster 6. */
        :>> opcodeLiteral = Opcode::GNC_RCS_THRUSTER_DISABLE_06; :>> opcodeNumber = 540; :>> mnemonic = "GNC_RCS_THRUSTER_DISABLE_06";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncRcsThrusterEnable07 : CommandDefinition {
        doc /* Enable reaction control thruster 7. */
        :>> opcodeLiteral = Opcode::GNC_RCS_THRUSTER_ENABLE_07; :>> opcodeNumber = 541; :>> mnemonic = "GNC_RCS_THRUSTER_ENABLE_07";
        :>> application = ApplicationName::gnc; :>> apidClass = ApidClass::guidance; :>> apid = 961;
        :>> allowedModes = allFlightModes; :>> criticality = CommandCriticality::critical; :>> hazardous = true;
        :>> argumentCount = 0; :>> argumentBits = 0;
    }
    item gncRcsThrusterDisable07 : CommandDefinition {
        doc /* Disable reaction control thruster 7. */
        :>> opcodeLiteral = Opcode::GNC_RCS_THRUSTER_DISABLE_07; :>> opcodeNumber = 542; :>> mnemonic = "GNC_RCS_THRUSTER_DISABLE_07";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncRcsThrusterEnable08 : CommandDefinition {
        doc /* Enable reaction control thruster 8. */
        :>> opcodeLiteral = Opcode::GNC_RCS_THRUSTER_ENABLE_08; :>> opcodeNumber = 543; :>> mnemonic = "GNC_RCS_THRUSTER_ENABLE_08";
        :>> application = ApplicationName::gnc; :>> apidClass = ApidClass::guidance; :>> apid = 961;
        :>> allowedModes = allFlightModes; :>> criticality = CommandCriticality::critical; :>> hazardous = true;
        :>> argumentCount = 0; :>> argumentBits = 0;
    }
    item gncRcsThrusterDisable08 : CommandDefinition {
        doc /* Disable reaction control thruster 8. */
        :>> opcodeLiteral = Opcode::GNC_RCS_THRUSTER_DISABLE_08; :>> opcodeNumber = 544; :>> mnemonic = "GNC_RCS_THRUSTER_DISABLE_08";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncWheelOn1 : CommandDefinition {
        doc /* Power on reaction wheel 1. */
        :>> opcodeLiteral = Opcode::GNC_WHEEL_ON_1; :>> opcodeNumber = 545; :>> mnemonic = "GNC_WHEEL_ON_1";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncWheelOff1 : CommandDefinition {
        doc /* Power off reaction wheel 1. */
        :>> opcodeLiteral = Opcode::GNC_WHEEL_OFF_1; :>> opcodeNumber = 546; :>> mnemonic = "GNC_WHEEL_OFF_1";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncWheelOn2 : CommandDefinition {
        doc /* Power on reaction wheel 2. */
        :>> opcodeLiteral = Opcode::GNC_WHEEL_ON_2; :>> opcodeNumber = 547; :>> mnemonic = "GNC_WHEEL_ON_2";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncWheelOff2 : CommandDefinition {
        doc /* Power off reaction wheel 2. */
        :>> opcodeLiteral = Opcode::GNC_WHEEL_OFF_2; :>> opcodeNumber = 548; :>> mnemonic = "GNC_WHEEL_OFF_2";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncWheelOn3 : CommandDefinition {
        doc /* Power on reaction wheel 3. */
        :>> opcodeLiteral = Opcode::GNC_WHEEL_ON_3; :>> opcodeNumber = 549; :>> mnemonic = "GNC_WHEEL_ON_3";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncWheelOff3 : CommandDefinition {
        doc /* Power off reaction wheel 3. */
        :>> opcodeLiteral = Opcode::GNC_WHEEL_OFF_3; :>> opcodeNumber = 550; :>> mnemonic = "GNC_WHEEL_OFF_3";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncWheelOn4 : CommandDefinition {
        doc /* Power on reaction wheel 4. */
        :>> opcodeLiteral = Opcode::GNC_WHEEL_ON_4; :>> opcodeNumber = 551; :>> mnemonic = "GNC_WHEEL_ON_4";
        :>> application = ApplicationName::gnc; :>> apidClass = ApidClass::guidance; :>> apid = 961;
        :>> allowedModes = allFlightModes; :>> criticality = CommandCriticality::critical; :>> hazardous = false;
        :>> argumentCount = 0; :>> argumentBits = 0;
    }
    item gncWheelOff4 : CommandDefinition {
        doc /* Power off reaction wheel 4. */
        :>> opcodeLiteral = Opcode::GNC_WHEEL_OFF_4; :>> opcodeNumber = 552; :>> mnemonic = "GNC_WHEEL_OFF_4";
        :>> application = ApplicationName::gnc; :>> apidClass = ApidClass::guidance; :>> apid = 961;
        :>> allowedModes = allFlightModes; :>> criticality = CommandCriticality::critical; :>> hazardous = false;
        :>> argumentCount = 0; :>> argumentBits = 0;
    }
    item sepStartThrustArc : CommandDefinition {
        doc /* Begin a thrust arc of the given duration at the given throttle. */
        :>> opcodeLiteral = Opcode::SEP_START_THRUST_ARC; :>> opcodeNumber = 769; :>> mnemonic = "SEP_START_THRUST_ARC";
        :>> application = ApplicationName::sepControl; :>> apidClass = ApidClass::propulsion; :>> apid = 962;
        :>> allowedModes = thrustingModes; :>> criticality = CommandCriticality::critical; :>> hazardous = true;
        :>> argumentCount = 2; :>> argumentBits = 48;
        attribute duration : DurationValue, CommandArgument { :>> minimum = 60.0; :>> maximum = 2592000.0; :>> widthBits = 32; }
        attribute throttle : Real, CommandArgument { :>> minimum = 0.2; :>> maximum = 1.0; :>> widthBits = 16; }
    }
    item sepStopThrust : CommandDefinition {
        doc /* Stop thrusting immediately and close the flow. */
        :>> opcodeLiteral = Opcode::SEP_STOP_THRUST; :>> opcodeNumber = 770; :>> mnemonic = "SEP_STOP_THRUST";
        :>> application = ApplicationName::sepControl; :>> apidClass = ApidClass::propulsion; :>> apid = 962;
        :>> allowedModes = allFlightModes; :>> criticality = CommandCriticality::critical; :>> hazardous = false;
        :>> argumentCount = 0; :>> argumentBits = 0;
    }
    item sepSetThrottle : CommandDefinition {
        doc /* Change the throttle of a running arc. */
        :>> opcodeLiteral = Opcode::SEP_SET_THROTTLE; :>> opcodeNumber = 771; :>> mnemonic = "SEP_SET_THROTTLE";
        :>> application = ApplicationName::sepControl; :>> apidClass = ApidClass::propulsion; :>> apid = 962;
        :>> allowedModes = thrustingModes; :>> criticality = CommandCriticality::critical; :>> hazardous = false;
        :>> argumentCount = 1; :>> argumentBits = 16;
        attribute throttle : Real, CommandArgument { :>> minimum = 0.2; :>> maximum = 1.0; :>> widthBits = 16; }
    }
    item sepSelectThruster : CommandDefinition {
        doc /* Select the thruster the next arc fires. */
        :>> opcodeLiteral = Opcode::SEP_SELECT_THRUSTER; :>> opcodeNumber = 772; :>> mnemonic = "SEP_SELECT_THRUSTER";
        :>> application = ApplicationName::sepControl; :>> apidClass = ApidClass::propulsion; :>> apid = 962;
        :>> allowedModes = allFlightModes; :>> criticality = CommandCriticality::critical; :>> hazardous = false;
        :>> argumentCount = 1; :>> argumentBits = 8;
        attribute thruster : Natural, CommandArgument { :>> minimum = 0.0; :>> maximum = 2.0; :>> widthBits = 8; }
    }
    item sepPrimeFeed : CommandDefinition {
        doc /* Open the feed system and bring the regulator to pressure. */
        :>> opcodeLiteral = Opcode::SEP_PRIME_FEED; :>> opcodeNumber = 773; :>> mnemonic = "SEP_PRIME_FEED";
        :>> application = ApplicationName::sepControl; :>> apidClass = ApidClass::propulsion; :>> apid = 962;
        :>> allowedModes = (TugMode::earlyOperations, thrustingModes, coastingModes, proximityModes, TugMode::capture, TugMode::despin, TugMode::droHold); :>> criticality = CommandCriticality::critical; :>> hazardous = true;
        :>> argumentCount = 0; :>> argumentBits = 0;
    }
    item sepVentFeed : CommandDefinition {
        doc /* Vent the feed lines downstream of the latch valves. */
        :>> opcodeLiteral = Opcode::SEP_VENT_FEED; :>> opcodeNumber = 774; :>> mnemonic = "SEP_VENT_FEED";
        :>> application = ApplicationName::sepControl; :>> apidClass = ApidClass::propulsion; :>> apid = 962;
        :>> allowedModes = (TugMode::earlyOperations, TugMode::coast, TugMode::droHold, TugMode::safe); :>> criticality = CommandCriticality::critical; :>> hazardous = true;
        :>> argumentCount = 0; :>> argumentBits = 0;
    }
    item sepSetFlowRate : CommandDefinition {
        doc /* Set the anode flow set point. */
        :>> opcodeLiteral = Opcode::SEP_SET_FLOW_RATE; :>> opcodeNumber = 775; :>> mnemonic = "SEP_SET_FLOW_RATE";
        :>> application = ApplicationName::sepControl; :>> apidClass = ApidClass::propulsion; :>> apid = 962;
        :>> allowedModes = thrustingModes; :>> criticality = CommandCriticality::critical; :>> hazardous = false;
        :>> argumentCount = 1; :>> argumentBits = 16;
        attribute flowFraction : Real, CommandArgument { :>> minimum = 0.5; :>> maximum = 1.2; :>> widthBits = 16; }
    }
    item sepThrusterRestart : CommandDefinition {
        doc /* Attempt a restart after a flameout, after the restart delay. */
        :>> opcodeLiteral = Opcode::SEP_THRUSTER_RESTART; :>> opcodeNumber = 776; :>> mnemonic = "SEP_THRUSTER_RESTART";
        :>> application = ApplicationName::sepControl; :>> apidClass = ApidClass::propulsion; :>> apid = 962;
        :>> allowedModes = thrustingModes; :>> criticality = CommandCriticality::critical; :>> hazardous = true;
        :>> argumentCount = 1; :>> argumentBits = 32;
        attribute delay : DurationValue, CommandArgument { :>> minimum = 60.0; :>> maximum = 86400.0; :>> widthBits = 32; }
    }
    item sepOpenLatchValve : CommandDefinition {
        doc /* Open a latch valve. */
        :>> opcodeLiteral = Opcode::SEP_OPEN_LATCH_VALVE; :>> opcodeNumber = 777; :>> mnemonic = "SEP_OPEN_LATCH_VALVE";
        :>> application = ApplicationName::sepControl; :>> apidClass = ApidClass::propulsion; :>> apid = 962;
        :>> allowedModes = allFlightModes; :>> criticality = CommandCriticality::critical; :>> hazardous = true;
        :>> argumentCount = 1; :>> argumentBits = 8;
        attribute valve : Natural, CommandArgument { :>> minimum = 0.0; :>> maximum = 5.0; :>> widthBits = 8; }
    }
    item sepCloseLatchValve : CommandDefinition {
        doc /* Close a latch valve. */
        :>> opcodeLiteral = Opcode::SEP_CLOSE_LATCH_VALVE; :>> opcodeNumber = 778; :>> mnemonic = "SEP_CLOSE_LATCH_VALVE";
        :>> application = ApplicationName::sepControl; :>> apidClass = ApidClass::propulsion; :>> apid = 962;
        :>> allowedModes = allFlightModes; :>> criticality = CommandCriticality::critical; :>> hazardous = false;
        :>> argumentCount = 1; :>> argumentBits = 8;
        attribute valve : Natural, CommandArgument { :>> minimum = 0.0; :>> maximum = 5.0; :>> widthBits = 8; }
    }
    item sepGimbalSet : CommandDefinition {
        doc /* Point a thruster gimbal. */
        :>> opcodeLiteral = Opcode::SEP_GIMBAL_SET; :>> opcodeNumber = 779; :>> mnemonic = "SEP_GIMBAL_SET";
        :>> application = ApplicationName::sepControl; :>> apidClass = ApidClass::propulsion; :>> apid = 962;
        :>> allowedModes = (TugMode::earlyOperations, thrustingModes, coastingModes, proximityModes, TugMode::capture, TugMode::despin, TugMode::droHold); :>> criticality = CommandCriticality::critical; :>> hazardous = false;
        :>> argumentCount = 3; :>> argumentBits = 72;
        attribute thruster : Natural, CommandArgument { :>> minimum = 0.0; :>> maximum = 2.0; :>> widthBits = 8; }
        attribute alpha : AngularMeasureValue, CommandArgument { :>> minimum = -0.2; :>> maximum = 0.2; :>> widthBits = 32; }
        attribute beta : AngularMeasureValue, CommandArgument { :>> minimum = -0.2; :>> maximum = 0.2; :>> widthBits = 32; }
    }
    item sepGimbalHome : CommandDefinition {
        doc /* Drive a thruster gimbal to its mechanical home. */
        :>> opcodeLiteral = Opcode::SEP_GIMBAL_HOME; :>> opcodeNumber = 780; :>> mnemonic = "SEP_GIMBAL_HOME";
        :>> application = ApplicationName::sepControl; :>> apidClass = ApidClass::propulsion; :>> apid = 962;
        :>> allowedModes = allFlightModes; :>> criticality = CommandCriticality::routine; :>> hazardous = false;
        :>> argumentCount = 1; :>> argumentBits = 8;
        attribute thruster : Natural, CommandArgument { :>> minimum = 0.0; :>> maximum = 2.0; :>> widthBits = 8; }
    }
    item sepSetDischargeLimit : CommandDefinition {
        doc /* Set the discharge current trip limit for the power processing units. */
        :>> opcodeLiteral = Opcode::SEP_SET_DISCHARGE_LIMIT; :>> opcodeNumber = 781; :>> mnemonic = "SEP_SET_DISCHARGE_LIMIT";
        :>> application = ApplicationName::sepControl; :>> apidClass = ApidClass::propulsion; :>> apid = 962;
        :>> allowedModes = (TugMode::earlyOperations, TugMode::coast, TugMode::droHold, TugMode::safe); :>> criticality = CommandCriticality::critical; :>> hazardous = false;
        :>> argumentCount = 1; :>> argumentBits = 16;
        attribute limit : ElectricCurrentValue, CommandArgument { :>> minimum = 5.0; :>> maximum = 40.0; :>> widthBits = 16; }
    }
    item sepTankHeaterSetpoint : CommandDefinition {
        doc /* Set the xenon tank heater set point. */
        :>> opcodeLiteral = Opcode::SEP_TANK_HEATER_SETPOINT; :>> opcodeNumber = 782; :>> mnemonic = "SEP_TANK_HEATER_SETPOINT";
        :>> application = ApplicationName::sepControl; :>> apidClass = ApidClass::propulsion; :>> apid = 962;
        :>> allowedModes = allFlightModes; :>> criticality = CommandCriticality::routine; :>> hazardous = false;
        :>> argumentCount = 1; :>> argumentBits = 16;
        attribute setpoint : ThermodynamicTemperatureValue, CommandArgument { :>> minimum = 273.0; :>> maximum = 323.0; :>> widthBits = 16; }
    }
    item sepPpuOn1 : CommandDefinition {
        doc /* Power on power processing unit 1. */
        :>> opcodeLiteral = Opcode::SEP_PPU_ON_1; :>> opcodeNumber = 783; :>> mnemonic = "SEP_PPU_ON_1";
        :>> application = ApplicationName::sepControl; :>> apidClass = ApidClass::propulsion; :>> apid = 962;
        :>> allowedModes = allFlightModes; :>> criticality = CommandCriticality::critical; :>> hazardous = true;
        :>> argumentCount = 0; :>> argumentBits = 0;
    }
    item sepPpuOff1 : CommandDefinition {
        doc /* Power off power processing unit 1. */
        :>> opcodeLiteral = Opcode::SEP_PPU_OFF_1; :>> opcodeNumber = 784; :>> mnemonic = "SEP_PPU_OFF_1";
        :>> application = ApplicationName::sepControl; :>> apidClass = ApidClass::propulsion; :>> apid = 962;
        :>> allowedModes = allFlightModes; :>> criticality = CommandCriticality::critical; :>> hazardous = false;
        :>> argumentCount = 0; :>> argumentBits = 0;
    }
    item sepPpuOn2 : CommandDefinition {
        doc /* Power on power processing unit 2. */
        :>> opcodeLiteral = Opcode::SEP_PPU_ON_2; :>> opcodeNumber = 785; :>> mnemonic = "SEP_PPU_ON_2";
        :>> application = ApplicationName::sepControl; :>> apidClass = ApidClass::propulsion; :>> apid = 962;
        :>> allowedModes = allFlightModes; :>> criticality = CommandCriticality::critical; :>> hazardous = true;
        :>> argumentCount = 0; :>> argumentBits = 0;
    }
    item sepPpuOff2 : CommandDefinition {
        doc /* Power off power processing unit 2. */
        :>> opcodeLiteral = Opcode::SEP_PPU_OFF_2; :>> opcodeNumber = 786; :>> mnemonic = "SEP_PPU_OFF_2";
        :>> application = ApplicationName::sepControl; :>> apidClass = ApidClass::propulsion; :>> apid = 962;
        :>> allowedModes = allFlightModes; :>> criticality = CommandCriticality::critical; :>> hazardous = false;
        :>> argumentCount = 0; :>> argumentBits = 0;
    }
    item sepPpuOn3 : CommandDefinition {
        doc /* Power on power processing unit 3. */
        :>> opcodeLiteral = Opcode::SEP_PPU_ON_3; :>> opcodeNumber = 787; :>> mnemonic = "SEP_PPU_ON_3";
        :>> application = ApplicationName::sepControl; :>> apidClass = ApidClass::propulsion; :>> apid = 962;
        :>> allowedModes = allFlightModes; :>> criticality = CommandCriticality::critical; :>> hazardous = true;
        :>> argumentCount = 0; :>> argumentBits = 0;
    }
    item sepPpuOff3 : CommandDefinition {
        doc /* Power off power processing unit 3. */
        :>> opcodeLiteral = Opcode::SEP_PPU_OFF_3; :>> opcodeNumber = 788; :>> mnemonic = "SEP_PPU_OFF_3";
        :>> application = ApplicationName::sepControl; :>> apidClass = ApidClass::propulsion; :>> apid = 962;
        :>> allowedModes = allFlightModes; :>> criticality = CommandCriticality::critical; :>> hazardous = false;
        :>> argumentCount = 0; :>> argumentBits = 0;
    }
    item sepCathodeHeaterOn1 : CommandDefinition {
        doc /* Enable the cathode heater of thruster 1. */
        :>> opcodeLiteral = Opcode::SEP_CATHODE_HEATER_ON_1; :>> opcodeNumber = 789; :>> mnemonic = "SEP_CATHODE_HEATER_ON_1";
        :>> application = ApplicationName::sepControl; :>> apidClass = ApidClass::propulsion; :>> apid = 962;
        :>> allowedModes = allFlightModes; :>> criticality = CommandCriticality::routine; :>> hazardous = false;
        :>> argumentCount = 0; :>> argumentBits = 0;
    }
    item sepCathodeHeaterOff1 : CommandDefinition {
        doc /* Disable the cathode heater of thruster 1. */
        :>> opcodeLiteral = Opcode::SEP_CATHODE_HEATER_OFF_1; :>> opcodeNumber = 790; :>> mnemonic = "SEP_CATHODE_HEATER_OFF_1";
        :>> application = ApplicationName::sepControl; :>> apidClass = ApidClass::propulsion; :>> apid = 962;
        :>> allowedModes = allFlightModes; :>> criticality = CommandCriticality::routine; :>> hazardous = false;
        :>> argumentCount = 0; :>> argumentBits = 0;
    }
    item sepCathodeHeaterOn2 : CommandDefinition {
        doc /* Enable the cathode heater of thruster 2. */
        :>> opcodeLiteral = Opcode::SEP_CATHODE_HEATER_ON_2; :>> opcodeNumber = 791; :>> mnemonic = "SEP_CATHODE_HEATER_ON_2";
        :>> application = ApplicationName::sepControl; :>> apidClass = ApidClass::propulsion; :>> apid = 962;
        :>> allowedModes = allFlightModes; :>> criticality = CommandCriticality::routine; :>> hazardous = false;
        :>> argumentCount = 0; :>> argumentBits = 0;
    }
    item sepCathodeHeaterOff2 : CommandDefinition {
        doc /* Disable the cathode heater of thruster 2. */
        :>> opcodeLiteral = Opcode::SEP_CATHODE_HEATER_OFF_2; :>> opcodeNumber = 792; :>> mnemonic = "SEP_CATHODE_HEATER_OFF_2";
        :>> application = ApplicationName::sepControl; :>> apidClass = ApidClass::propulsion; :>> apid = 962;
        :>> allowedModes = allFlightModes; :>> criticality = CommandCriticality::routine; :>> hazardous = false;
        :>> argumentCount = 0; :>> argumentBits = 0;
    }
    item sepCathodeHeaterOn3 : CommandDefinition {
        doc /* Enable the cathode heater of thruster 3. */
        :>> opcodeLiteral = Opcode::SEP_CATHODE_HEATER_ON_3; :>> opcodeNumber = 793; :>> mnemonic = "SEP_CATHODE_HEATER_ON_3";
        :>> application = ApplicationName::sepControl; :>> apidClass = ApidClass::propulsion; :>> apid = 962;
        :>> allowedModes = allFlightModes; :>> criticality = CommandCriticality::routine; :>> hazardous = false;
        :>> argumentCount = 0; :>> argumentBits = 0;
    }
    item sepCathodeHeaterOff3 : CommandDefinition {
        doc /* Disable the cathode heater of thruster 3. */
        :>> opcodeLiteral = Opcode::SEP_CATHODE_HEATER_OFF_3; :>> opcodeNumber = 794; :>> mnemonic = "SEP_CATHODE_HEATER_OFF_3";
        :>> application = ApplicationName::sepControl; :>> apidClass = ApidClass::propulsion; :>> apid = 962;
        :>> allowedModes = allFlightModes; :>> criticality = CommandCriticality::routine; :>> hazardous = false;
        :>> argumentCount = 0; :>> argumentBits = 0;
    }
    item epsSetBatteryChargeLimit : CommandDefinition {
        doc /* Set the battery end-of-charge voltage. */
        :>> opcodeLiteral = Opcode::EPS_SET_BATTERY_CHARGE_LIMIT; :>> opcodeNumber = 1025; :>> mnemonic = "EPS_SET_BATTERY_CHARGE_LIMIT";
        :>> application = ApplicationName::powerManagement; :>> apidClass = ApidClass::housekeeping; :>> apid = 963;
        :>> allowedModes = allFlightModes; :>> criticality = CommandCriticality::critical; :>> hazardous = false;
        :>> argumentCount = 1; :>> argumentBits = 16;
        attribute voltage : ElectricPotentialValue, CommandArgument { :>> minimum = 28.0; :>> maximum = 33.6; :>> widthBits = 16; }
    }
    item epsSetLoadShedLevel : CommandDefinition {
        doc /* Set the load-shed tier the power manager applies at low state of charge. */
        :>> opcodeLiteral = Opcode::EPS_SET_LOAD_SHED_LEVEL; :>> opcodeNumber = 1026; :>> mnemonic = "EPS_SET_LOAD_SHED_LEVEL";
        :>> application = ApplicationName::powerManagement; :>> apidClass = ApidClass::housekeeping; :>> apid = 963;
        :>> allowedModes = allFlightModes; :>> criticality = CommandCriticality::critical; :>> hazardous = false;
        :>> argumentCount = 1; :>> argumentBits = 8;
        attribute level : Natural, CommandArgument { :>> minimum = 0.0; :>> maximum = 3.0; :>> widthBits = 8; }
    }
    item epsSelectBattery : CommandDefinition {
        doc /* Select the battery that carries the bus; the other floats. */
        :>> opcodeLiteral = Opcode::EPS_SELECT_BATTERY; :>> opcodeNumber = 1027; :>> mnemonic = "EPS_SELECT_BATTERY";
        :>> application = ApplicationName::powerManagement; :>> apidClass = ApidClass::housekeeping; :>> apid = 963;
        :>> allowedModes = allFlightModes; :>> criticality = CommandCriticality::critical; :>> hazardous = false;
        :>> argumentCount = 1; :>> argumentBits = 8;
        attribute battery : Natural, CommandArgument { :>> minimum = 0.0; :>> maximum = 1.0; :>> widthBits = 8; }
    }
    item epsSadaSetAngle : CommandDefinition {
        doc /* Drive a solar array drive to an angle. */
        :>> opcodeLiteral = Opcode::EPS_SADA_SET_ANGLE; :>> opcodeNumber = 1028; :>> mnemonic = "EPS_SADA_SET_ANGLE";
        :>> application = ApplicationName::powerManagement; :>> apidClass = ApidClass::housekeeping; :>> apid = 963;
        :>> allowedModes = (TugMode::earlyOperations, thrustingModes, coastingModes, proximityModes, TugMode::capture, TugMode::despin, TugMode::droHold); :>> criticality = CommandCriticality::critical; :>> hazardous = false;
        :>> argumentCount = 2; :>> argumentBits = 40;
        attribute drive : Natural, CommandArgument { :>> minimum = 0.0; :>> maximum = 1.0; :>> widthBits = 8; }
        attribute angle : AngularMeasureValue, CommandArgument { :>> minimum = -3.14159; :>> maximum = 3.14159; :>> widthBits = 32; }
    }
    item epsSadaTrackSun : CommandDefinition {
        doc /* Return a solar array drive to sun tracking. */
        :>> opcodeLiteral = Opcode::EPS_SADA_TRACK_SUN; :>> opcodeNumber = 1029; :>> mnemonic = "EPS_SADA_TRACK_SUN";
        :>> application = ApplicationName::powerManagement; :>> apidClass = ApidClass::housekeeping; :>> apid = 963;
        :>> allowedModes = allFlightModes; :>> criticality = CommandCriticality::routine; :>> hazardous = false;
        :>> argumentCount = 1; :>> argumentBits = 8;
        attribute drive : Natural, CommandArgument { :>> minimum = 0.0; :>> maximum = 1.0; :>> widthBits = 8; }
    }
    item epsSadaHold : CommandDefinition {
        doc /* Hold a solar array drive at its current angle. */
        :>> opcodeLiteral = Opcode::EPS_SADA_HOLD; :>> opcodeNumber = 1030; :>> mnemonic = "EPS_SADA_HOLD";
        :>> application = ApplicationName::powerManagement; :>> apidClass = ApidClass::housekeeping; :>> apid = 963;
        :>> allowedModes = allFlightModes; :>> criticality = CommandCriticality::routine; :>> hazardous = false;
        :>> argumentCount = 1; :>> argumentBits = 8;
        attribute drive : Natural, CommandArgument { :>> minimum = 0.0; :>> maximum = 1.0; :>> widthBits = 8; }
    }
    item epsSetBusVoltageLimits : CommandDefinition {
        doc /* Set the regulated bus under- and over-voltage trips. */
        :>> opcodeLiteral = Opcode::EPS_SET_BUS_VOLTAGE_LIMITS; :>> opcodeNumber = 1031; :>> mnemonic = "EPS_SET_BUS_VOLTAGE_LIMITS";
        :>> application = ApplicationName::powerManagement; :>> apidClass = ApidClass::housekeeping; :>> apid = 963;
        :>> allowedModes = (TugMode::earlyOperations, TugMode::coast, TugMode::droHold, TugMode::safe); :>> criticality = CommandCriticality::critical; :>> hazardous = false;
        :>> argumentCount = 2; :>> argumentBits = 32;
        attribute lowTrip : ElectricPotentialValue, CommandArgument { :>> minimum = 24.0; :>> maximum = 28.0; :>> widthBits = 16; }
        attribute highTrip : ElectricPotentialValue, CommandArgument { :>> minimum = 28.0; :>> maximum = 32.0; :>> widthBits = 16; }
    }
    item epsBalanceCells : CommandDefinition {
        doc /* Start a cell balancing cycle on a battery. */
        :>> opcodeLiteral = Opcode::EPS_BALANCE_CELLS; :>> opcodeNumber = 1032; :>> mnemonic = "EPS_BALANCE_CELLS";
        :>> application = ApplicationName::powerManagement; :>> apidClass = ApidClass::housekeeping; :>> apid = 963;
        :>> allowedModes = allFlightModes; :>> criticality = CommandCriticality::routine; :>> hazardous = false;
        :>> argumentCount = 1; :>> argumentBits = 8;
        attribute battery : Natural, CommandArgument { :>> minimum = 0.0; :>> maximum = 1.0; :>> widthBits = 8; }
    }
    item epsResetSwitchTrips : CommandDefinition {
        doc /* Clear every latched over-current trip. */
        :>> opcodeLiteral = Opcode::EPS_RESET_SWITCH_TRIPS; :>> opcodeNumber = 1033; :>> mnemonic = "EPS_RESET_SWITCH_TRIPS";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSetArrayStringMask : CommandDefinition {
        doc /* Mask solar array strings out of the regulator. */
        :>> opcodeLiteral = Opcode::EPS_SET_ARRAY_STRING_MASK; :>> opcodeNumber = 1034; :>> mnemonic = "EPS_SET_ARRAY_STRING_MASK";
        :>> application = ApplicationName::powerManagement; :>> apidClass = ApidClass::housekeeping; :>> apid = 963;
        :>> allowedModes = allFlightModes; :>> criticality = CommandCriticality::critical; :>> hazardous = false;
        :>> argumentCount = 2; :>> argumentBits = 16;
        attribute wing : Natural, CommandArgument { :>> minimum = 0.0; :>> maximum = 3.0; :>> widthBits = 8; }
        attribute mask : Natural, CommandArgument { :>> minimum = 0.0; :>> maximum = 63.0; :>> widthBits = 8; }
    }
    item epsSwitchOn01 : CommandDefinition {
        doc /* Close power switch 1. */
        :>> opcodeLiteral = Opcode::EPS_SWITCH_ON_01; :>> opcodeNumber = 1035; :>> mnemonic = "EPS_SWITCH_ON_01";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff01 : CommandDefinition {
        doc /* Open power switch 1. */
        :>> opcodeLiteral = Opcode::EPS_SWITCH_OFF_01; :>> opcodeNumber = 1036; :>> mnemonic = "EPS_SWITCH_OFF_01";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn02 : CommandDefinition {
        doc /* Close power switch 2. */
        :>> opcodeLiteral = Opcode::EPS_SWITCH_ON_02; :>> opcodeNumber = 1037; :>> mnemonic = "EPS_SWITCH_ON_02";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff02 : CommandDefinition {
        doc /* Open power switch 2. */
        :>> opcodeLiteral = Opcode::EPS_SWITCH_OFF_02; :>> opcodeNumber = 1038; :>> mnemonic = "EPS_SWITCH_OFF_02";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn03 : CommandDefinition {
        doc /* Close power switch 3. */
        :>> opcodeLiteral = Opcode::EPS_SWITCH_ON_03; :>> opcodeNumber = 1039; :>> mnemonic = "EPS_SWITCH_ON_03";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff03 : CommandDefinition {
        doc /* Open power switch 3. */
        :>> opcodeLiteral = Opcode::EPS_SWITCH_OFF_03; :>> opcodeNumber = 1040; :>> mnemonic = "EPS_SWITCH_OFF_03";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn04 : CommandDefinition {
        doc /* Close power switch 4. */
        :>> opcodeLiteral = Opcode::EPS_SWITCH_ON_04; :>> opcodeNumber = 1041; :>> mnemonic = "EPS_SWITCH_ON_04";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff04 : CommandDefinition {
        doc /* Open power switch 4. */
        :>> opcodeLiteral = Opcode::EPS_SWITCH_OFF_04; :>> opcodeNumber = 1042; :>> mnemonic = "EPS_SWITCH_OFF_04";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn05 : CommandDefinition {
        doc /* Close power switch 5. */
        :>> opcodeLiteral = Opcode::EPS_SWITCH_ON_05; :>> opcodeNumber = 1043; :>> mnemonic = "EPS_SWITCH_ON_05";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff05 : CommandDefinition {
        doc /* Open power switch 5. */
        :>> opcodeLiteral = Opcode::EPS_SWITCH_OFF_05; :>> opcodeNumber = 1044; :>> mnemonic = "EPS_SWITCH_OFF_05";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn06 : CommandDefinition {
        doc /* Close power switch 6. */
        :>> opcodeLiteral = Opcode::EPS_SWITCH_ON_06; :>> opcodeNumber = 1045; :>> mnemonic = "EPS_SWITCH_ON_06";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff06 : CommandDefinition {
        doc /* Open power switch 6. */
        :>> opcodeLiteral = Opcode::EPS_SWITCH_OFF_06; :>> opcodeNumber = 1046; :>> mnemonic = "EPS_SWITCH_OFF_06";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn07 : CommandDefinition {
        doc /* Close power switch 7. */
        :>> opcodeLiteral = Opcode::EPS_SWITCH_ON_07; :>> opcodeNumber = 1047; :>> mnemonic = "EPS_SWITCH_ON_07";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff07 : CommandDefinition {
        doc /* Open power switch 7. */
        :>> opcodeLiteral = Opcode::EPS_SWITCH_OFF_07; :>> opcodeNumber = 1048; :>> mnemonic = "EPS_SWITCH_OFF_07";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn08 : CommandDefinition {
        doc /* Close power switch 8. */
        :>> opcodeLiteral = Opcode::EPS_SWITCH_ON_08; :>> opcodeNumber = 1049; :>> mnemonic = "EPS_SWITCH_ON_08";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff08 : CommandDefinition {
        doc /* Open power switch 8. */
        :>> opcodeLiteral = Opcode::EPS_SWITCH_OFF_08; :>> opcodeNumber = 1050; :>> mnemonic = "EPS_SWITCH_OFF_08";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn09 : CommandDefinition {
        doc /* Close power switch 9. */
        :>> opcodeLiteral = Opcode::EPS_SWITCH_ON_09; :>> opcodeNumber = 1051; :>> mnemonic = "EPS_SWITCH_ON_09";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff09 : CommandDefinition {
        doc /* Open power switch 9. */
        :>> opcodeLiteral = Opcode::EPS_SWITCH_OFF_09; :>> opcodeNumber = 1052; :>> mnemonic = "EPS_SWITCH_OFF_09";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn10 : CommandDefinition {
        doc /* Close power switch 10. */
        :>> opcodeLiteral = Opcode::EPS_SWITCH_ON_10; :>> opcodeNumber = 1053; :>> mnemonic = "EPS_SWITCH_ON_10";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff10 : CommandDefinition {
        doc /* Open power switch 10. */
        :>> opcodeLiteral = Opcode::EPS_SWITCH_OFF_10; :>> opcodeNumber = 1054; :>> mnemonic = "EPS_SWITCH_OFF_10";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn11 : CommandDefinition {
        doc /* Close power switch 11. */
        :>> opcodeLiteral = Opcode::EPS_SWITCH_ON_11; :>> opcodeNumber = 1055; :>> mnemonic = "EPS_SWITCH_ON_11";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff11 : CommandDefinition {
        doc /* Open power switch 11. */
        :>> opcodeLiteral = Opcode::EPS_SWITCH_OFF_11; :>> opcodeNumber = 1056; :>> mnemonic = "EPS_SWITCH_OFF_11";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn12 : CommandDefinition {
        doc /* Close power switch 12. */
        :>> opcodeLiteral = Opcode::EPS_SWITCH_ON_12; :>> opcodeNumber = 1057; :>> mnemonic = "EPS_SWITCH_ON_12";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff12 : CommandDefinition {
        doc /* Open power switch 12. */
        :>> opcodeLiteral = Opcode::EPS_SWITCH_OFF_12; :>> opcodeNumber = 1058; :>> mnemonic = "EPS_SWITCH_OFF_12";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn13 : CommandDefinition {
        doc /* Close power switch 13. */
        :>> opcodeLiteral = Opcode::EPS_SWITCH_ON_13; :>> opcodeNumber = 1059; :>> mnemonic = "EPS_SWITCH_ON_13";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff13 : CommandDefinition {
        doc /* Open power switch 13. */
        :>> opcodeLiteral = Opcode::EPS_SWITCH_OFF_13; :>> opcodeNumber = 1060; :>> mnemonic = "EPS_SWITCH_OFF_13";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn14 : CommandDefinition {
        doc /* Close power switch 14. */
        :>> opcodeLiteral = Opcode::EPS_SWITCH_ON_14; :>> opcodeNumber = 1061; :>> mnemonic = "EPS_SWITCH_ON_14";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff14 : CommandDefinition {
        doc /* Open power switch 14. */
        :>> opcodeLiteral = Opcode::EPS_SWITCH_OFF_14; :>> opcodeNumber = 1062; :>> mnemonic = "EPS_SWITCH_OFF_14";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn15 : CommandDefinition {
        doc /* Close power switch 15. */
        :>> opcodeLiteral = Opcode::EPS_SWITCH_ON_15; :>> opcodeNumber = 1063; :>> mnemonic = "EPS_SWITCH_ON_15";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff15 : CommandDefinition {
        doc /* Open power switch 15. */
        :>> opcodeLiteral = Opcode::EPS_SWITCH_OFF_15; :>> opcodeNumber = 1064; :>> mnemonic = "EPS_SWITCH_OFF_15";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn16 : CommandDefinition {
        doc /* Close power switch 16. */
        :>> opcodeLiteral = Opcode::EPS_SWITCH_ON_16; :>> opcodeNumber = 1065; :>> mnemonic = "EPS_SWITCH_ON_16";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff16 : CommandDefinition {
        doc /* Open power switch 16. */
        :>> opcodeLiteral = Opcode::EPS_SWITCH_OFF_16; :>> opcodeNumber = 1066; :>> mnemonic = "EPS_SWITCH_OFF_16";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn17 : CommandDefinition {
        doc /* Close power switch 17. */
        :>> opcodeLiteral = Opcode::EPS_SWITCH_ON_17; :>> opcodeNumber = 1067; :>> mnemonic = "EPS_SWITCH_ON_17";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff17 : CommandDefinition {
        doc /* Open power switch 17. */
        :>> opcodeLiteral = Opcode::EPS_SWITCH_OFF_17; :>> opcodeNumber = 1068; :>> mnemonic = "EPS_SWITCH_OFF_17";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn18 : CommandDefinition {
        doc /* Close power switch 18. */
        :>> opcodeLiteral = Opcode::EPS_SWITCH_ON_18; :>> opcodeNumber = 1069; :>> mnemonic = "EPS_SWITCH_ON_18";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff18 : CommandDefinition {
        doc /* Open power switch 18. */
        :>> opcodeLiteral = Opcode::EPS_SWITCH_OFF_18; :>> opcodeNumber = 1070; :>> mnemonic = "EPS_SWITCH_OFF_18";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn19 : CommandDefinition {
        doc /* Close power switch 19. */
        :>> opcodeLiteral = Opcode::EPS_SWITCH_ON_19; :>> opcodeNumber = 1071; :>> mnemonic = "EPS_SWITCH_ON_19";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff19 : CommandDefinition {
        doc /* Open power switch 19. */
        :>> opcodeLiteral = Opcode::EPS_SWITCH_OFF_19; :>> opcodeNumber = 1072; :>> mnemonic = "EPS_SWITCH_OFF_19";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn20 : CommandDefinition {
        doc /* Close power switch 20. */
        :>> opcodeLiteral = Opcode::EPS_SWITCH_ON_20; :>> opcodeNumber = 1073; :>> mnemonic = "EPS_SWITCH_ON_20";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff20 : CommandDefinition {
        doc /* Open power switch 20. */
        :>> opcodeLiteral = Opcode::EPS_SWITCH_OFF_20; :>> opcodeNumber = 1074; :>> mnemonic = "EPS_SWITCH_OFF_20";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn21 : CommandDefinition {
        doc /* Close power switch 21. */
        :>> opcodeLiteral = Opcode::EPS_SWITCH_ON_21; :>> opcodeNumber = 1075; :>> mnemonic = "EPS_SWITCH_ON_21";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff21 : CommandDefinition {
        doc /* Open power switch 21. */
        :>> opcodeLiteral = Opcode::EPS_SWITCH_OFF_21; :>> opcodeNumber = 1076; :>> mnemonic = "EPS_SWITCH_OFF_21";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn22 : CommandDefinition {
        doc /* Close power switch 22. */
        :>> opcodeLiteral = Opcode::EPS_SWITCH_ON_22; :>> opcodeNumber = 1077; :>> mnemonic = "EPS_SWITCH_ON_22";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff22 : CommandDefinition {
        doc /* Open power switch 22. */
        :>> opcodeLiteral = Opcode::EPS_SWITCH_OFF_22; :>> opcodeNumber = 1078; :>> mnemonic = "EPS_SWITCH_OFF_22";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn23 : CommandDefinition {
        doc /* Close power switch 23. */
        :>> opcodeLiteral = Opcode::EPS_SWITCH_ON_23; :>> opcodeNumber = 1079; :>> mnemonic = "EPS_SWITCH_ON_23";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff23 : CommandDefinition {
        doc /* Open power switch 23. */
        :>> opcodeLiteral = Opcode::EPS_SWITCH_OFF_23; :>> opcodeNumber = 1080; :>> mnemonic = "EPS_SWITCH_OFF_23";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOn24 : CommandDefinition {
        doc /* Close power switch 24. */
        :>> opcodeLiteral = Opcode::EPS_SWITCH_ON_24; :>> opcodeNumber = 1081; :>> mnemonic = "EPS_SWITCH_ON_24";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item epsSwitchOff24 : CommandDefinition {
        doc /* Open power switch 24. */
        :>> opcodeLiteral = Opcode::EPS_SWITCH_OFF_24; :>> opcodeNumber = 1082; :>> mnemonic = "EPS_SWITCH_OFF_24";
        :>> application = ApplicationName::powerManagement; :>> apidClass = ApidClass::housekeeping; :>> apid = 963;
        :>> allowedModes = allFlightModes; :>> criticality = CommandCriticality::critical; :>> hazardous = false;
        :>> argumentCount = 0; :>> argumentBits = 0;
    }
    item thmSetControlMode : CommandDefinition {
        doc /* Select the heater control law: bang-bang, proportional or open loop. */
        :>> opcodeLiteral = Opcode::THM_SET_CONTROL_MODE; :>> opcodeNumber = 1281; :>> mnemonic = "THM_SET_CONTROL_MODE";
        :>> application = ApplicationName::thermalControl; :>> apidClass = ApidClass::housekeeping; :>> apid = 964;
        :>> allowedModes = allFlightModes; :>> criticality = CommandCriticality::critical; :>> hazardous = false;
        :>> argumentCount = 1; :>> argumentBits = 8;
        attribute law : Natural, CommandArgument { :>> minimum = 0.0; :>> maximum = 2.0; :>> widthBits = 8; }
    }
    item thmLouverSet : CommandDefinition {
        doc /* Set a radiator louver position. */
        :>> opcodeLiteral = Opcode::THM_LOUVER_SET; :>> opcodeNumber = 1282; :>> mnemonic = "THM_LOUVER_SET";
        :>> application = ApplicationName::thermalControl; :>> apidClass = ApidClass::housekeeping; :>> apid = 964;
        :>> allowedModes = allFlightModes; :>> criticality = CommandCriticality::routine; :>> hazardous = false;
        :>> argumentCount = 2; :>> argumentBits = 24;
        attribute louver : Natural, CommandArgument { :>> minimum = 0.0; :>> maximum = 3.0; :>> widthBits = 8; }
        attribute position : Real, CommandArgument { :>> minimum = 0.0; :>> maximum = 1.0; :>> widthBits = 16; }
    }
    item thmLouverAuto : CommandDefinition {
        doc /* Return a radiator louver to passive control. */
        :>> opcodeLiteral = Opcode::THM_LOUVER_AUTO; :>> opcodeNumber = 1283; :>> mnemonic = "THM_LOUVER_AUTO";
        :>> application = ApplicationName::thermalControl; :>> apidClass = ApidClass::housekeeping; :>> apid = 964;
        :>> allowedModes = allFlightModes; :>> criticality = CommandCriticality::routine; :>> hazardous = false;
        :>> argumentCount = 1; :>> argumentBits = 8;
        attribute louver : Natural, CommandArgument { :>> minimum = 0.0; :>> maximum = 3.0; :>> widthBits = 8; }
    }
    item thmSetSurvivalSetpoints : CommandDefinition {
        doc /* Set the survival heater set points applied in safe mode. */
        :>> opcodeLiteral = Opcode::THM_SET_SURVIVAL_SETPOINTS; :>> opcodeNumber = 1284; :>> mnemonic = "THM_SET_SURVIVAL_SETPOINTS";
        :>> application = ApplicationName::thermalControl; :>> apidClass = ApidClass::housekeeping; :>> apid = 964;
        :>> allowedModes = (TugMode::earlyOperations, TugMode::coast, TugMode::droHold, TugMode::safe); :>> criticality = CommandCriticality::critical; :>> hazardous = false;
        :>> argumentCount = 2; :>> argumentBits = 32;
        attribute low : ThermodynamicTemperatureValue, CommandArgument { :>> minimum = 233.0; :>> maximum = 283.0; :>> widthBits = 16; }
        attribute high : ThermodynamicTemperatureValue, CommandArgument { :>> minimum = 243.0; :>> maximum = 293.0; :>> widthBits = 16; }
    }
    item thmSetDeadband : CommandDefinition {
        doc /* Set the control deadband of every zone. */
        :>> opcodeLiteral = Opcode::THM_SET_DEADBAND; :>> opcodeNumber = 1285; :>> mnemonic = "THM_SET_DEADBAND";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute deadband : ThermodynamicTemperatureValue, CommandArgument { :>> minimum = 0.5; :>> maximum = 10.0; :>> widthBits = 16; }
    }
    item thmEnableAllHeaters : CommandDefinition {
        doc /* Enable every heater zone under its set point. */
        :>> opcodeLiteral = Opcode::THM_ENABLE_ALL_HEATERS; :>> opcodeNumber = 1286; :>> mnemonic = "THM_ENABLE_ALL_HEATERS";
        :>> application = ApplicationName::thermalControl; :>> apidClass = ApidClass::housekeeping; :>> apid = 964;
        :>> allowedModes = allFlightModes; :>> criticality = CommandCriticality::critical; :>> hazardous = false;
        :>> argumentCount = 0; :>> argumentBits = 0;
    }
    item thmDisableAllHeaters : CommandDefinition {
        doc /* Disable every heater zone; survival heaters stay on their thermostats. */
        :>> opcodeLiteral = Opcode::THM_DISABLE_ALL_HEATERS; :>> opcodeNumber = 1287; :>> mnemonic = "THM_DISABLE_ALL_HEATERS";
        :>> application = ApplicationName::thermalControl; :>> apidClass = ApidClass::housekeeping; :>> apid = 964;
        :>> allowedModes = allFlightModes; :>> criticality = CommandCriticality::critical; :>> hazardous = true;
        :>> argumentCount = 0; :>> argumentBits = 0;
    }
    item thmSetHeaterPowerCap : CommandDefinition {
        doc /* Cap the total heater power the thermal application may draw. */
        :>> opcodeLiteral = Opcode::THM_SET_HEATER_POWER_CAP; :>> opcodeNumber = 1288; :>> mnemonic = "THM_SET_HEATER_POWER_CAP";
        :>> application = ApplicationName::thermalControl; :>> apidClass = ApidClass::housekeeping; :>> apid = 964;
        :>> allowedModes = allFlightModes; :>> criticality = CommandCriticality::critical; :>> hazardous = false;
        :>> argumentCount = 1; :>> argumentBits = 16;
        attribute cap : PowerValue, CommandArgument { :>> minimum = 50.0; :>> maximum = 900.0; :>> widthBits = 16; }
    }
    item thmHeaterEnable01 : CommandDefinition {
        doc /* Enable heater zone 1. */
        :>> opcodeLiteral = Opcode::THM_HEATER_ENABLE_01; :>> opcodeNumber = 1289; :>> mnemonic = "THM_HEATER_ENABLE_01";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable01 : CommandDefinition {
        doc /* Disable heater zone 1. */
        :>> opcodeLiteral = Opcode::THM_HEATER_DISABLE_01; :>> opcodeNumber = 1290; :>> mnemonic = "THM_HEATER_DISABLE_01";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable02 : CommandDefinition {
        doc /* Enable heater zone 2. */
        :>> opcodeLiteral = Opcode::THM_HEATER_ENABLE_02; :>> opcodeNumber = 1291; :>> mnemonic = "THM_HEATER_ENABLE_02";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable02 : CommandDefinition {
        doc /* Disable heater zone 2. */
        :>> opcodeLiteral = Opcode::THM_HEATER_DISABLE_02; :>> opcodeNumber = 1292; :>> mnemonic = "THM_HEATER_DISABLE_02";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable03 : CommandDefinition {
        doc /* Enable heater zone 3. */
        :>> opcodeLiteral = Opcode::THM_HEATER_ENABLE_03; :>> opcodeNumber = 1293; :>> mnemonic = "THM_HEATER_ENABLE_03";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable03 : CommandDefinition {
        doc /* Disable heater zone 3. */
        :>> opcodeLiteral = Opcode::THM_HEATER_DISABLE_03; :>> opcodeNumber = 1294; :>> mnemonic = "THM_HEATER_DISABLE_03";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable04 : CommandDefinition {
        doc /* Enable heater zone 4. */
        :>> opcodeLiteral = Opcode::THM_HEATER_ENABLE_04; :>> opcodeNumber = 1295; :>> mnemonic = "THM_HEATER_ENABLE_04";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable04 : CommandDefinition {
        doc /* Disable heater zone 4. */
        :>> opcodeLiteral = Opcode::THM_HEATER_DISABLE_04; :>> opcodeNumber = 1296; :>> mnemonic = "THM_HEATER_DISABLE_04";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable05 : CommandDefinition {
        doc /* Enable heater zone 5. */
        :>> opcodeLiteral = Opcode::THM_HEATER_ENABLE_05; :>> opcodeNumber = 1297; :>> mnemonic = "THM_HEATER_ENABLE_05";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable05 : CommandDefinition {
        doc /* Disable heater zone 5. */
        :>> opcodeLiteral = Opcode::THM_HEATER_DISABLE_05; :>> opcodeNumber = 1298; :>> mnemonic = "THM_HEATER_DISABLE_05";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable06 : CommandDefinition {
        doc /* Enable heater zone 6. */
        :>> opcodeLiteral = Opcode::THM_HEATER_ENABLE_06; :>> opcodeNumber = 1299; :>> mnemonic = "THM_HEATER_ENABLE_06";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable06 : CommandDefinition {
        doc /* Disable heater zone 6. */
        :>> opcodeLiteral = Opcode::THM_HEATER_DISABLE_06; :>> opcodeNumber = 1300; :>> mnemonic = "THM_HEATER_DISABLE_06";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable07 : CommandDefinition {
        doc /* Enable heater zone 7. */
        :>> opcodeLiteral = Opcode::THM_HEATER_ENABLE_07; :>> opcodeNumber = 1301; :>> mnemonic = "THM_HEATER_ENABLE_07";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable07 : CommandDefinition {
        doc /* Disable heater zone 7. */
        :>> opcodeLiteral = Opcode::THM_HEATER_DISABLE_07; :>> opcodeNumber = 1302; :>> mnemonic = "THM_HEATER_DISABLE_07";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable08 : CommandDefinition {
        doc /* Enable heater zone 8. */
        :>> opcodeLiteral = Opcode::THM_HEATER_ENABLE_08; :>> opcodeNumber = 1303; :>> mnemonic = "THM_HEATER_ENABLE_08";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable08 : CommandDefinition {
        doc /* Disable heater zone 8. */
        :>> opcodeLiteral = Opcode::THM_HEATER_DISABLE_08; :>> opcodeNumber = 1304; :>> mnemonic = "THM_HEATER_DISABLE_08";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable09 : CommandDefinition {
        doc /* Enable heater zone 9. */
        :>> opcodeLiteral = Opcode::THM_HEATER_ENABLE_09; :>> opcodeNumber = 1305; :>> mnemonic = "THM_HEATER_ENABLE_09";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable09 : CommandDefinition {
        doc /* Disable heater zone 9. */
        :>> opcodeLiteral = Opcode::THM_HEATER_DISABLE_09; :>> opcodeNumber = 1306; :>> mnemonic = "THM_HEATER_DISABLE_09";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable10 : CommandDefinition {
        doc /* Enable heater zone 10. */
        :>> opcodeLiteral = Opcode::THM_HEATER_ENABLE_10; :>> opcodeNumber = 1307; :>> mnemonic = "THM_HEATER_ENABLE_10";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable10 : CommandDefinition {
        doc /* Disable heater zone 10. */
        :>> opcodeLiteral = Opcode::THM_HEATER_DISABLE_10; :>> opcodeNumber = 1308; :>> mnemonic = "THM_HEATER_DISABLE_10";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable11 : CommandDefinition {
        doc /* Enable heater zone 11. */
        :>> opcodeLiteral = Opcode::THM_HEATER_ENABLE_11; :>> opcodeNumber = 1309; :>> mnemonic = "THM_HEATER_ENABLE_11";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable11 : CommandDefinition {
        doc /* Disable heater zone 11. */
        :>> opcodeLiteral = Opcode::THM_HEATER_DISABLE_11; :>> opcodeNumber = 1310; :>> mnemonic = "THM_HEATER_DISABLE_11";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable12 : CommandDefinition {
        doc /* Enable heater zone 12. */
        :>> opcodeLiteral = Opcode::THM_HEATER_ENABLE_12; :>> opcodeNumber = 1311; :>> mnemonic = "THM_HEATER_ENABLE_12";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable12 : CommandDefinition {
        doc /* Disable heater zone 12. */
        :>> opcodeLiteral = Opcode::THM_HEATER_DISABLE_12; :>> opcodeNumber = 1312; :>> mnemonic = "THM_HEATER_DISABLE_12";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable13 : CommandDefinition {
        doc /* Enable heater zone 13. */
        :>> opcodeLiteral = Opcode::THM_HEATER_ENABLE_13; :>> opcodeNumber = 1313; :>> mnemonic = "THM_HEATER_ENABLE_13";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable13 : CommandDefinition {
        doc /* Disable heater zone 13. */
        :>> opcodeLiteral = Opcode::THM_HEATER_DISABLE_13; :>> opcodeNumber = 1314; :>> mnemonic = "THM_HEATER_DISABLE_13";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable14 : CommandDefinition {
        doc /* Enable heater zone 14. */
        :>> opcodeLiteral = Opcode::THM_HEATER_ENABLE_14; :>> opcodeNumber = 1315; :>> mnemonic = "THM_HEATER_ENABLE_14";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable14 : CommandDefinition {
        doc /* Disable heater zone 14. */
        :>> opcodeLiteral = Opcode::THM_HEATER_DISABLE_14; :>> opcodeNumber = 1316; :>> mnemonic = "THM_HEATER_DISABLE_14";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable15 : CommandDefinition {
        doc /* Enable heater zone 15. */
        :>> opcodeLiteral = Opcode::THM_HEATER_ENABLE_15; :>> opcodeNumber = 1317; :>> mnemonic = "THM_HEATER_ENABLE_15";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable15 : CommandDefinition {
        doc /* Disable heater zone 15. */
        :>> opcodeLiteral = Opcode::THM_HEATER_DISABLE_15; :>> opcodeNumber = 1318; :>> mnemonic = "THM_HEATER_DISABLE_15";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterEnable16 : CommandDefinition {
        doc /* Enable heater zone 16. */
        :>> opcodeLiteral = Opcode::THM_HEATER_ENABLE_16; :>> opcodeNumber = 1319; :>> mnemonic = "THM_HEATER_ENABLE_16";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterDisable16 : CommandDefinition {
        doc /* Disable heater zone 16. */
        :>> opcodeLiteral = Opcode::THM_HEATER_DISABLE_16; :>> opcodeNumber = 1320; :>> mnemonic = "THM_HEATER_DISABLE_16";
        :>> application = ApplicationName::thermalControl; :>> apidClass = ApidClass::housekeeping; :>> apid = 964;
        :>> allowedModes = allFlightModes; :>> criticality = CommandCriticality::routine; :>> hazardous = false;
        :>> argumentCount = 0; :>> argumentBits = 0;
    }
    item thmHeaterSetpoint01 : CommandDefinition {
        doc /* Set the control set point of heater zone 1. */
        :>> opcodeLiteral = Opcode::THM_HEATER_SETPOINT_01; :>> opcodeNumber = 1321; :>> mnemonic = "THM_HEATER_SETPOINT_01";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint02 : CommandDefinition {
        doc /* Set the control set point of heater zone 2. */
        :>> opcodeLiteral = Opcode::THM_HEATER_SETPOINT_02; :>> opcodeNumber = 1322; :>> mnemonic = "THM_HEATER_SETPOINT_02";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint03 : CommandDefinition {
        doc /* Set the control set point of heater zone 3. */
        :>> opcodeLiteral = Opcode::THM_HEATER_SETPOINT_03; :>> opcodeNumber = 1323; :>> mnemonic = "THM_HEATER_SETPOINT_03";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint04 : CommandDefinition {
        doc /* Set the control set point of heater zone 4. */
        :>> opcodeLiteral = Opcode::THM_HEATER_SETPOINT_04; :>> opcodeNumber = 1324; :>> mnemonic = "THM_HEATER_SETPOINT_04";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint05 : CommandDefinition {
        doc /* Set the control set point of heater zone 5. */
        :>> opcodeLiteral = Opcode::THM_HEATER_SETPOINT_05; :>> opcodeNumber = 1325; :>> mnemonic = "THM_HEATER_SETPOINT_05";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint06 : CommandDefinition {
        doc /* Set the control set point of heater zone 6. */
        :>> opcodeLiteral = Opcode::THM_HEATER_SETPOINT_06; :>> opcodeNumber = 1326; :>> mnemonic = "THM_HEATER_SETPOINT_06";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint07 : CommandDefinition {
        doc /* Set the control set point of heater zone 7. */
        :>> opcodeLiteral = Opcode::THM_HEATER_SETPOINT_07; :>> opcodeNumber = 1327; :>> mnemonic = "THM_HEATER_SETPOINT_07";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint08 : CommandDefinition {
        doc /* Set the control set point of heater zone 8. */
        :>> opcodeLiteral = Opcode::THM_HEATER_SETPOINT_08; :>> opcodeNumber = 1328; :>> mnemonic = "THM_HEATER_SETPOINT_08";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint09 : CommandDefinition {
        doc /* Set the control set point of heater zone 9. */
        :>> opcodeLiteral = Opcode::THM_HEATER_SETPOINT_09; :>> opcodeNumber = 1329; :>> mnemonic = "THM_HEATER_SETPOINT_09";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint10 : CommandDefinition {
        doc /* Set the control set point of heater zone 10. */
        :>> opcodeLiteral = Opcode::THM_HEATER_SETPOINT_10; :>> opcodeNumber = 1330; :>> mnemonic = "THM_HEATER_SETPOINT_10";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint11 : CommandDefinition {
        doc /* Set the control set point of heater zone 11. */
        :>> opcodeLiteral = Opcode::THM_HEATER_SETPOINT_11; :>> opcodeNumber = 1331; :>> mnemonic = "THM_HEATER_SETPOINT_11";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint12 : CommandDefinition {
        doc /* Set the control set point of heater zone 12. */
        :>> opcodeLiteral = Opcode::THM_HEATER_SETPOINT_12; :>> opcodeNumber = 1332; :>> mnemonic = "THM_HEATER_SETPOINT_12";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint13 : CommandDefinition {
        doc /* Set the control set point of heater zone 13. */
        :>> opcodeLiteral = Opcode::THM_HEATER_SETPOINT_13; :>> opcodeNumber = 1333; :>> mnemonic = "THM_HEATER_SETPOINT_13";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint14 : CommandDefinition {
        doc /* Set the control set point of heater zone 14. */
        :>> opcodeLiteral = Opcode::THM_HEATER_SETPOINT_14; :>> opcodeNumber = 1334; :>> mnemonic = "THM_HEATER_SETPOINT_14";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint15 : CommandDefinition {
        doc /* Set the control set point of heater zone 15. */
        :>> opcodeLiteral = Opcode::THM_HEATER_SETPOINT_15; :>> opcodeNumber = 1335; :>> mnemonic = "THM_HEATER_SETPOINT_15";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item thmHeaterSetpoint16 : CommandDefinition {
        doc /* Set the control set point of heater zone 16. */
        :>> opcodeLiteral = Opcode::THM_HEATER_SETPOINT_16; :>> opcodeNumber = 1336; :>> mnemonic = "THM_HEATER_SETPOINT_16";
        :>> application = ApplicationName::thermalControl; :>> apidClass = ApidClass::housekeeping; :>> apid = 964;
        :>> allowedModes = allFlightModes; :>> criticality = CommandCriticality::routine; :>> hazardous = false;
        :>> argumentCount = 1; :>> argumentBits = 16;
        attribute setpoint : ThermodynamicTemperatureValue, CommandArgument { :>> minimum = 233.0; :>> maximum = 323.0; :>> widthBits = 16; }
    }
    item comTransmitterOn : CommandDefinition {
        doc /* Enable the transmitter on the selected transponder. */
        :>> opcodeLiteral = Opcode::COM_TRANSMITTER_ON; :>> opcodeNumber = 1537; :>> mnemonic = "COM_TRANSMITTER_ON";
        :>> application = ApplicationName::telecom; :>> apidClass = ApidClass::relay; :>> apid = 965;
        :>> allowedModes = allFlightModes; :>> criticality = CommandCriticality::critical; :>> hazardous = true;
        :>> argumentCount = 1; :>> argumentBits = 8;
        attribute transponder : Natural, CommandArgument { :>> minimum = 0.0; :>> maximum = 1.0; :>> widthBits = 8; }
    }
    item comTransmitterOff : CommandDefinition {
        doc /* Disable the transmitter. */
        :>> opcodeLiteral = Opcode::COM_TRANSMITTER_OFF; :>> opcodeNumber = 1538; :>> mnemonic = "COM_TRANSMITTER_OFF";
        :>> application = ApplicationName::telecom; :>> apidClass = ApidClass::relay; :>> apid = 965;
        :>> allowedModes = allFlightModes; :>> criticality = CommandCriticality::critical; :>> hazardous = false;
        :>> argumentCount = 1; :>> argumentBits = 8;
        attribute transponder : Natural, CommandArgument { :>> minimum = 0.0; :>> maximum = 1.0; :>> widthBits = 8; }
    }
    item comSelectTransponder : CommandDefinition {
        doc /* Select the prime transponder. */
        :>> opcodeLiteral = Opcode::COM_SELECT_TRANSPONDER; :>> opcodeNumber = 1539; :>> mnemonic = "COM_SELECT_TRANSPONDER";
        :>> application = ApplicationName::telecom; :>> apidClass = ApidClass::relay; :>> apid = 965;
        :>> allowedModes = allFlightModes; :>> criticality = CommandCriticality::critical; :>> hazardous = false;
        :>> argumentCount = 1; :>> argumentBits = 8;
        attribute transponder : Natural, CommandArgument { :>> minimum = 0.0; :>> maximum = 1.0; :>> widthBits = 8; }
    }
    item comSelectAntenna : CommandDefinition {
        doc /* Route the transmitter to the high-gain or a low-gain antenna. */
        :>> opcodeLiteral = Opcode::COM_SELECT_ANTENNA; :>> opcodeNumber = 1540; :>> mnemonic = "COM_SELECT_ANTENNA";
        :>> application = ApplicationName::telecom; :>> apidClass = ApidClass::relay; :>> apid = 965;
        :>> allowedModes = allFlightModes; :>> criticality = CommandCriticality::critical; :>> hazardous = false;
        :>> argumentCount = 1; :>> argumentBits = 8;
        attribute antenna : Natural, CommandArgument { :>> minimum = 0.0; :>> maximum = 2.0; :>> widthBits = 8; }
    }
    item comSetDownlinkRate : CommandDefinition {
        doc /* Set the downlink symbol rate. */
        :>> opcodeLiteral = Opcode::COM_SET_DOWNLINK_RATE; :>> opcodeNumber = 1541; :>> mnemonic = "COM_SET_DOWNLINK_RATE";
        :>> application = ApplicationName::telecom; :>> apidClass = ApidClass::relay; :>> apid = 965;
        :>> allowedModes = allFlightModes; :>> criticality = CommandCriticality::routine; :>> hazardous = false;
        :>> argumentCount = 1; :>> argumentBits = 32;
        attribute rate : FrequencyValue, CommandArgument { :>> minimum = 10.0; :>> maximum = 4000000.0; :>> widthBits = 32; }
    }
    item comSetUplinkRate : CommandDefinition {
        doc /* Set the expected uplink bit rate. */
        :>> opcodeLiteral = Opcode::COM_SET_UPLINK_RATE; :>> opcodeNumber = 1542; :>> mnemonic = "COM_SET_UPLINK_RATE";
        :>> application = ApplicationName::telecom; :>> apidClass = ApidClass::relay; :>> apid = 965;
        :>> allowedModes = allFlightModes; :>> criticality = CommandCriticality::routine; :>> hazardous = false;
        :>> argumentCount = 1; :>> argumentBits = 32;
        attribute rate : FrequencyValue, CommandArgument { :>> minimum = 7.8125; :>> maximum = 4000.0; :>> widthBits = 32; }
    }
    item comRangingOn : CommandDefinition {
        doc /* Enable the ranging channel turn-around. */
        :>> opcodeLiteral = Opcode::COM_RANGING_ON; :>> opcodeNumber = 1543; :>> mnemonic = "COM_RANGING_ON";
        :>> application = ApplicationName::telecom; :>> apidClass = ApidClass::relay; :>> apid = 965;
        :>> allowedModes = allFlightModes; :>> criticality = CommandCriticality::routine; :>> hazardous = false;
        :>> argumentCount = 0; :>> argumentBits = 0;
    }
    item comRangingOff : CommandDefinition {
        doc /* Disable the ranging channel turn-around. */
        :>> opcodeLiteral = Opcode::COM_RANGING_OFF; :>> opcodeNumber = 1544; :>> mnemonic = "COM_RANGING_OFF";
        :>> application = ApplicationName::telecom; :>> apidClass = ApidClass::relay; :>> apid = 965;
        :>> allowedModes = allFlightModes; :>> criticality = CommandCriticality::routine; :>> hazardous = false;
        :>> argumentCount = 0; :>> argumentBits = 0;
    }
    item comHgaPoint : CommandDefinition {
        doc /* Point the high-gain antenna. */
        :>> opcodeLiteral = Opcode::COM_HGA_POINT; :>> opcodeNumber = 1545; :>> mnemonic = "COM_HGA_POINT";
        :>> application = ApplicationName::telecom; :>> apidClass = ApidClass::relay; :>> apid = 965;
        :>> allowedModes = (TugMode::earlyOperations, thrustingModes, coastingModes, proximityModes, TugMode::capture, TugMode::despin, TugMode::droHold); :>> criticality = CommandCriticality::critical; :>> hazardous = false;
        :>> argumentCount = 2; :>> argumentBits = 64;
        attribute azimuth : AngularMeasureValue, CommandArgument { :>> minimum = -1.5708; :>> maximum = 1.5708; :>> widthBits = 32; }
        attribute elevation : AngularMeasureValue, CommandArgument { :>> minimum = -0.7854; :>> maximum = 0.7854; :>> widthBits = 32; }
    }
    item comHgaTrackEarth : CommandDefinition {
        doc /* Return the high-gain antenna to Earth tracking. */
        :>> opcodeLiteral = Opcode::COM_HGA_TRACK_EARTH; :>> opcodeNumber = 1546; :>> mnemonic = "COM_HGA_TRACK_EARTH";
        :>> application = ApplicationName::telecom; :>> apidClass = ApidClass::relay; :>> apid = 965;
        :>> allowedModes = allFlightModes; :>> criticality = CommandCriticality::routine; :>> hazardous = false;
        :>> argumentCount = 0; :>> argumentBits = 0;
    }
    item comHgaStow : CommandDefinition {
        doc /* Stow the high-gain antenna. */
        :>> opcodeLiteral = Opcode::COM_HGA_STOW; :>> opcodeNumber = 1547; :>> mnemonic = "COM_HGA_STOW";
        :>> application = ApplicationName::telecom; :>> apidClass = ApidClass::relay; :>> apid = 965;
        :>> allowedModes = allFlightModes; :>> criticality = CommandCriticality::critical; :>> hazardous = false;
        :>> argumentCount = 0; :>> argumentBits = 0;
    }
    item comSetPassWindow : CommandDefinition {
        doc /* Load the next ground pass window. */
        :>> opcodeLiteral = Opcode::COM_SET_PASS_WINDOW; :>> opcodeNumber = 1548; :>> mnemonic = "COM_SET_PASS_WINDOW";
        :>> application = ApplicationName::telecom; :>> apidClass = ApidClass::relay; :>> apid = 965;
        :>> allowedModes = allFlightModes; :>> criticality = CommandCriticality::routine; :>> hazardous = false;
        :>> argumentCount = 2; :>> argumentBits = 64;
        attribute windowStart : Natural, CommandArgument { :>> minimum = 0.0; :>> maximum = 4294967295.0; :>> widthBits = 32; }
        attribute duration : DurationValue, CommandArgument { :>> minimum = 600.0; :>> maximum = 43200.0; :>> widthBits = 32; }
    }
    item comSetCoding : CommandDefinition {
        doc /* Select the downlink coding: convolutional, Reed–Solomon, turbo or LDPC. */
        :>> opcodeLiteral = Opcode::COM_SET_CODING; :>> opcodeNumber = 1549; :>> mnemonic = "COM_SET_CODING";
        :>> application = ApplicationName::telecom; :>> apidClass = ApidClass::relay; :>> apid = 965;
        :>> allowedModes = allFlightModes; :>> criticality = CommandCriticality::routine; :>> hazardous = false;
        :>> argumentCount = 1; :>> argumentBits = 8;
        attribute code : Natural, CommandArgument { :>> minimum = 0.0; :>> maximum = 3.0; :>> widthBits = 8; }
    }
    item comSetTransmitPower : CommandDefinition {
        doc /* Set the transmitter output power. */
        :>> opcodeLiteral = Opcode::COM_SET_TRANSMIT_POWER; :>> opcodeNumber = 1550; :>> mnemonic = "COM_SET_TRANSMIT_POWER";
        :>> application = ApplicationName::telecom; :>> apidClass = ApidClass::relay; :>> apid = 965;
        :>> allowedModes = allFlightModes; :>> criticality = CommandCriticality::critical; :>> hazardous = false;
        :>> argumentCount = 1; :>> argumentBits = 16;
        attribute power : PowerValue, CommandArgument { :>> minimum = 5.0; :>> maximum = 100.0; :>> widthBits = 16; }
    }
    item comDownlinkRatePreset1 : CommandDefinition {
        doc /* Select downlink rate preset 1 of the link table. */
        :>> opcodeLiteral = Opcode::COM_DOWNLINK_RATE_PRESET_1; :>> opcodeNumber = 1551; :>> mnemonic = "COM_DOWNLINK_RATE_PRESET_1";
        :>> application = ApplicationName::telecom; :>> apidClass = ApidClass::relay; :>> apid = 965;
        :>> allowedModes = allFlightModes; :>> criticality = CommandCriticality::routine; :>> hazardous = false;
        :>> argumentCount = 0; :>> argumentBits = 0;
    }
    item comDownlinkRatePreset2 : CommandDefinition {
        doc /* Select downlink rate preset 2 of the link table. */
        :>> opcodeLiteral = Opcode::COM_DOWNLINK_RATE_PRESET_2; :>> opcodeNumber = 1552; :>> mnemonic = "COM_DOWNLINK_RATE_PRESET_2";
        :>> application = ApplicationName::telecom; :>> apidClass = ApidClass::relay; :>> apid = 965;
        :>> allowedModes = allFlightModes; :>> criticality = CommandCriticality::routine; :>> hazardous = false;
        :>> argumentCount = 0; :>> argumentBits = 0;
    }
    item comDownlinkRatePreset3 : CommandDefinition {
        doc /* Select downlink rate preset 3 of the link table. */
        :>> opcodeLiteral = Opcode::COM_DOWNLINK_RATE_PRESET_3; :>> opcodeNumber = 1553; :>> mnemonic = "COM_DOWNLINK_RATE_PRESET_3";
        :>> application = ApplicationName::telecom; :>> apidClass = ApidClass::relay; :>> apid = 965;
        :>> allowedModes = allFlightModes; :>> criticality = CommandCriticality::routine; :>> hazardous = false;
        :>> argumentCount = 0; :>> argumentBits = 0;
    }
    item comDownlinkRatePreset4 : CommandDefinition {
        doc /* Select downlink rate preset 4 of the link table. */
        :>> opcodeLiteral = Opcode::COM_DOWNLINK_RATE_PRESET_4; :>> opcodeNumber = 1554; :>> mnemonic = "COM_DOWNLINK_RATE_PRESET_4";
        :>> application = ApplicationName::telecom; :>> apidClass = ApidClass::relay; :>> apid = 965;
        :>> allowedModes = allFlightModes; :>> criticality = CommandCriticality::routine; :>> hazardous = false;
        :>> argumentCount = 0; :>> argumentBits = 0;
    }
    item comDownlinkRatePreset5 : CommandDefinition {
        doc /* Select downlink rate preset 5 of the link table. */
        :>> opcodeLiteral = Opcode::COM_DOWNLINK_RATE_PRESET_5; :>> opcodeNumber = 1555; :>> mnemonic = "COM_DOWNLINK_RATE_PRESET_5";
        :>> application = ApplicationName::telecom; :>> apidClass = ApidClass::relay; :>> apid = 965;
        :>> allowedModes = allFlightModes; :>> criticality = CommandCriticality::routine; :>> hazardous = false;
        :>> argumentCount = 0; :>> argumentBits = 0;
    }
    item comDownlinkRatePreset6 : CommandDefinition {
        doc /* Select downlink rate preset 6 of the link table. */
        :>> opcodeLiteral = Opcode::COM_DOWNLINK_RATE_PRESET_6; :>> opcodeNumber = 1556; :>> mnemonic = "COM_DOWNLINK_RATE_PRESET_6";
        :>> application = ApplicationName::telecom; :>> apidClass = ApidClass::relay; :>> apid = 965;
        :>> allowedModes = allFlightModes; :>> criticality = CommandCriticality::routine; :>> hazardous = false;
        :>> argumentCount = 0; :>> argumentBits = 0;
    }
    item insArmRelease : CommandDefinition {
        doc /* Arm the inspector release mechanism. */
        :>> opcodeLiteral = Opcode::INS_ARM_RELEASE; :>> opcodeNumber = 1793; :>> mnemonic = "INS_ARM_RELEASE";
        :>> application = ApplicationName::inspectorHandling; :>> apidClass = ApidClass::imaging; :>> apid = 966;
        :>> allowedModes = (TugMode::proximityOperations); :>> criticality = CommandCriticality::critical; :>> hazardous = true;
        :>> argumentCount = 1; :>> argumentBits = 16;
        attribute armKey : Natural, CommandArgument { :>> minimum = 0.0; :>> maximum = 65535.0; :>> widthBits = 16; }
    }
    item insSafeRelease : CommandDefinition {
        doc /* Disarm the inspector release mechanism. */
        :>> opcodeLiteral = Opcode::INS_SAFE_RELEASE; :>> opcodeNumber = 1794; :>> mnemonic = "INS_SAFE_RELEASE";
        :>> application = ApplicationName::inspectorHandling; :>> apidClass = ApidClass::imaging; :>> apid = 966;
        :>> allowedModes = allFlightModes; :>> criticality = CommandCriticality::critical; :>> hazardous = false;
        :>> argumentCount = 0; :>> argumentBits = 0;
    }
    item insReleaseInspector : CommandDefinition {
        doc /* Release the inspector; irreversible. */
        :>> opcodeLiteral = Opcode::INS_RELEASE_INSPECTOR; :>> opcodeNumber = 1795; :>> mnemonic = "INS_RELEASE_INSPECTOR";
        :>> application = ApplicationName::inspectorHandling; :>> apidClass = ApidClass::imaging; :>> apid = 966;
        :>> allowedModes = (TugMode::proximityOperations); :>> criticality = CommandCriticality::hazardous; :>> hazardous = true;
        :>> argumentCount = 2; :>> argumentBits = 32;
        attribute releaseSpeed : SpeedValue, CommandArgument { :>> minimum = 0.02; :>> maximum = 0.2; :>> widthBits = 16; }
        attribute confirmKey : Natural, CommandArgument { :>> minimum = 0.0; :>> maximum = 65535.0; :>> widthBits = 16; }
    }
    item insForwardCommand : CommandDefinition {
        doc /* Forward a command block to the inspector over the relay link. */
        :>> opcodeLiteral = Opcode::INS_FORWARD_COMMAND; :>> opcodeNumber = 1796; :>> mnemonic = "INS_FORWARD_COMMAND";
        :>> application = ApplicationName::inspectorHandling; :>> apidClass = ApidClass::imaging; :>> apid = 966;
        :>> allowedModes = proximityModes; :>> criticality = CommandCriticality::critical; :>> hazardous = false;
        :>> argumentCount = 2; :>> argumentBits = 32;
        attribute inspectorOpcode : Natural, CommandArgument { :>> minimum = 0.0; :>> maximum = 65535.0; :>> widthBits = 16; }
        attribute byteCount : Natural, CommandArgument { :>> minimum = 0.0; :>> maximum = 1024.0; :>> widthBits = 16; }
    }
    item insStartImagingSession : CommandDefinition {
        doc /* Start an inspector imaging session of the given duration. */
        :>> opcodeLiteral = Opcode::INS_START_IMAGING_SESSION; :>> opcodeNumber = 1797; :>> mnemonic = "INS_START_IMAGING_SESSION";
        :>> application = ApplicationName::inspectorHandling; :>> apidClass = ApidClass::imaging; :>> apid = 966;
        :>> allowedModes = proximityModes; :>> criticality = CommandCriticality::routine; :>> hazardous = false;
        :>> argumentCount = 2; :>> argumentBits = 48;
        attribute duration : DurationValue, CommandArgument { :>> minimum = 60.0; :>> maximum = 7200.0; :>> widthBits = 32; }
        attribute cadence : DurationValue, CommandArgument { :>> minimum = 1.0; :>> maximum = 600.0; :>> widthBits = 16; }
    }
    item insStopImagingSession : CommandDefinition {
        doc /* Stop the inspector imaging session. */
        :>> opcodeLiteral = Opcode::INS_STOP_IMAGING_SESSION; :>> opcodeNumber = 1798; :>> mnemonic = "INS_STOP_IMAGING_SESSION";
        :>> application = ApplicationName::inspectorHandling; :>> apidClass = ApidClass::imaging; :>> apid = 966;
        :>> allowedModes = allFlightModes; :>> criticality = CommandCriticality::routine; :>> hazardous = false;
        :>> argumentCount = 0; :>> argumentBits = 0;
    }
    item insSetImageCompression : CommandDefinition {
        doc /* Set the image compression ratio relayed to the inspector. */
        :>> opcodeLiteral = Opcode::INS_SET_IMAGE_COMPRESSION; :>> opcodeNumber = 1799; :>> mnemonic = "INS_SET_IMAGE_COMPRESSION";
        :>> application = ApplicationName::inspectorHandling; :>> apidClass = ApidClass::imaging; :>> apid = 966;
        :>> allowedModes = allFlightModes; :>> criticality = CommandCriticality::routine; :>> hazardous = false;
        :>> argumentCount = 1; :>> argumentBits = 8;
        attribute ratio : Natural, CommandArgument { :>> minimum = 1.0; :>> maximum = 20.0; :>> widthBits = 8; }
    }
    item insSelectRelayRate : CommandDefinition {
        doc /* Set the relay link data rate. */
        :>> opcodeLiteral = Opcode::INS_SELECT_RELAY_RATE; :>> opcodeNumber = 1800; :>> mnemonic = "INS_SELECT_RELAY_RATE";
        :>> application = ApplicationName::inspectorHandling; :>> apidClass = ApidClass::imaging; :>> apid = 966;
        :>> allowedModes = allFlightModes; :>> criticality = CommandCriticality::routine; :>> hazardous = false;
        :>> argumentCount = 1; :>> argumentBits = 32;
        attribute rate : FrequencyValue, CommandArgument { :>> minimum = 1000.0; :>> maximum = 2000000.0; :>> widthBits = 32; }
    }
    item insStoreImageSegment : CommandDefinition {
        doc /* Store a relayed image segment in the recorder. */
        :>> opcodeLiteral = Opcode::INS_STORE_IMAGE_SEGMENT; :>> opcodeNumber = 1801; :>> mnemonic = "INS_STORE_IMAGE_SEGMENT";
        :>> application = ApplicationName::inspectorHandling; :>> apidClass = ApidClass::imaging; :>> apid = 966;
        :>> allowedModes = allFlightModes; :>> criticality = CommandCriticality::routine; :>> hazardous = false;
        :>> argumentCount = 2; :>> argumentBits = 32;
        attribute imageId : Natural, CommandArgument { :>> minimum = 0.0; :>> maximum = 65535.0; :>> widthBits = 16; }
        attribute segment : Natural, CommandArgument { :>> minimum = 0.0; :>> maximum = 4095.0; :>> widthBits = 16; }
    }
    item insDownlinkImage : CommandDefinition {
        doc /* Queue a stored inspector image for downlink. */
        :>> opcodeLiteral = Opcode::INS_DOWNLINK_IMAGE; :>> opcodeNumber = 1802; :>> mnemonic = "INS_DOWNLINK_IMAGE";
        :>> application = ApplicationName::inspectorHandling; :>> apidClass = ApidClass::imaging; :>> apid = 966;
        :>> allowedModes = allFlightModes; :>> criticality = CommandCriticality::routine; :>> hazardous = false;
        :>> argumentCount = 1; :>> argumentBits = 16;
        attribute imageId : Natural, CommandArgument { :>> minimum = 0.0; :>> maximum = 65535.0; :>> widthBits = 16; }
    }
    item insRetireInspector : CommandDefinition {
        doc /* Command the inspector to its disposal state; irreversible. */
        :>> opcodeLiteral = Opcode::INS_RETIRE_INSPECTOR; :>> opcodeNumber = 1803; :>> mnemonic = "INS_RETIRE_INSPECTOR";
        :>> application = ApplicationName::inspectorHandling; :>> apidClass = ApidClass::imaging; :>> apid = 966;
        :>> allowedModes = (TugMode::capture, TugMode::despin, TugMode::stackCoast); :>> criticality = CommandCriticality::hazardous; :>> hazardous = true;
        :>> argumentCount = 1; :>> argumentBits = 16;
        attribute confirmKey : Natural, CommandArgument { :>> minimum = 0.0; :>> maximum = 65535.0; :>> widthBits = 16; }
    }
    item insSetRelayWindow : CommandDefinition {
        doc /* Load the next relay contact window. */
        :>> opcodeLiteral = Opcode::INS_SET_RELAY_WINDOW; :>> opcodeNumber = 1804; :>> mnemonic = "INS_SET_RELAY_WINDOW";
        :>> application = ApplicationName::inspectorHandling; :>> apidClass = ApidClass::imaging; :>> apid = 966;
        :>> allowedModes = allFlightModes; :>> criticality = CommandCriticality::routine; :>> hazardous = false;
        :>> argumentCount = 2; :>> argumentBits = 64;
        attribute windowStart : Natural, CommandArgument { :>> minimum = 0.0; :>> maximum = 4294967295.0; :>> widthBits = 32; }
        attribute duration : DurationValue, CommandArgument { :>> minimum = 60.0; :>> maximum = 86400.0; :>> widthBits = 32; }
    }
    item insEnableRelay : CommandDefinition {
        doc /* Enable the relay receiver. */
        :>> opcodeLiteral = Opcode::INS_ENABLE_RELAY; :>> opcodeNumber = 1805; :>> mnemonic = "INS_ENABLE_RELAY";
        :>> application = ApplicationName::inspectorHandling; :>> apidClass = ApidClass::imaging; :>> apid = 966;
        :>> allowedModes = allFlightModes; :>> criticality = CommandCriticality::routine; :>> hazardous = false;
        :>> argumentCount = 0; :>> argumentBits = 0;
    }
    item insDisableRelay : CommandDefinition {
        doc /* Disable the relay receiver. */
        :>> opcodeLiteral = Opcode::INS_DISABLE_RELAY; :>> opcodeNumber = 1806; :>> mnemonic = "INS_DISABLE_RELAY";
        :>> application = ApplicationName::inspectorHandling; :>> apidClass = ApidClass::imaging; :>> apid = 966;
        :>> allowedModes = allFlightModes; :>> criticality = CommandCriticality::routine; :>> hazardous = false;
        :>> argumentCount = 0; :>> argumentBits = 0;
    }
    item capArmCapture : CommandDefinition {
        doc /* Arm the capture mechanism. */
        :>> opcodeLiteral = Opcode::CAP_ARM_CAPTURE; :>> opcodeNumber = 2049; :>> mnemonic = "CAP_ARM_CAPTURE";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 1; :>> argumentBits = 16;
        attribute armKey : Natural, CommandArgument { :>> minimum = 0.0; :>> maximum = 65535.0; :>> widthBits = 16; }
    }
    item capDisarmCapture : CommandDefinition {
        doc /* Disarm the capture mechanism. */
        :>> opcodeLiteral = Opcode::CAP_DISARM_CAPTURE; :>> opcodeNumber = 2050; :>> mnemonic = "CAP_DISARM_CAPTURE";
        :>> application = ApplicationName::captureControl; :>> apidClass = ApidClass::capture; :>> apid = 967;
        :>> allowedModes = allFlightModes; :>> criticality = CommandCriticality::critical; :>> hazardous = false;
        :>> argumentCount = 0; :>> argumentBits = 0;
    }
    item capDeployBag : CommandDefinition {
        doc /* Deploy the capture bag. */
        :>> opcodeLiteral = Opcode::CAP_DEPLOY_BAG; :>> opcodeNumber = 2051; :>> mnemonic = "CAP_DEPLOY_BAG";
        :>> application = ApplicationName::captureControl; :>> apidClass = ApidClass::capture; :>> apid = 967;
        :>> allowedModes = (TugMode::proximityOperations, TugMode::capture); :>> criticality = CommandCriticality::hazardous; :>> hazardous = true;
        :>> argumentCount = 1; :>> argumentBits = 16;
        attribute confirmKey : Natural, CommandArgument { :>> minimum = 0.0; :>> maximum = 65535.0; :>> widthBits = 16; }
    }
    item capCloseBag : CommandDefinition {
        doc /* Close the capture bag around the body. */
        :>> opcodeLiteral = Opcode::CAP_CLOSE_BAG; :>> opcodeNumber = 2052; :>> mnemonic = "CAP_CLOSE_BAG";
        :>> application = ApplicationName::captureControl; :>> apidClass = ApidClass::capture; :>> apid = 967;
        :>> allowedModes = (TugMode::capture); :>> criticality = CommandCriticality::hazardous; :>> hazardous = true;
        :>> argumentCount = 1; :>> argumentBits = 16;
        attribute confirmKey : Natural, CommandArgument { :>> minimum = 0.0; :>> maximum = 65535.0; :>> widthBits = 16; }
    }
    item capCinchBag : CommandDefinition {
        doc /* Cinch the bag to the commanded tension. */
        :>> opcodeLiteral = Opcode::CAP_CINCH_BAG; :>> opcodeNumber = 2053; :>> mnemonic = "CAP_CINCH_BAG";
        :>> application = ApplicationName::captureControl; :>> apidClass = ApidClass::capture; :>> apid = 967;
        :>> allowedModes = (TugMode::capture, TugMode::despin); :>> criticality = CommandCriticality::critical; :>> hazardous = true;
        :>> argumentCount = 1; :>> argumentBits = 16;
        attribute tension : ForceValue, CommandArgument { :>> minimum = 10.0; :>> maximum = 2000.0; :>> widthBits = 16; }
    }
    item capStartDespin : CommandDefinition {
        doc /* Start the despin controller. */
        :>> opcodeLiteral = Opcode::CAP_START_DESPIN; :>> opcodeNumber = 2054; :>> mnemonic = "CAP_START_DESPIN";
        :>> application = ApplicationName::captureControl; :>> apidClass = ApidClass::capture; :>> apid = 967;
        :>> allowedModes = (TugMode::despin); :>> criticality = CommandCriticality::critical; :>> hazardous = true;
        :>> argumentCount = 1; :>> argumentBits = 16;
        attribute torqueLimit : Real, CommandArgument { :>> minimum = 0.1; :>> maximum = 1.0; :>> widthBits = 16; }
    }
    item capStopDespin : CommandDefinition {
        doc /* Stop the despin controller. */
        :>> opcodeLiteral = Opcode::CAP_STOP_DESPIN; :>> opcodeNumber = 2055; :>> mnemonic = "CAP_STOP_DESPIN";
        :>> application = ApplicationName::captureControl; :>> apidClass = ApidClass::capture; :>> apid = 967;
        :>> allowedModes = allFlightModes; :>> criticality = CommandCriticality::critical; :>> hazardous = false;
        :>> argumentCount = 0; :>> argumentBits = 0;
    }
    item capSetDespinTorque : CommandDefinition {
        doc /* Set the despin torque fraction. */
        :>> opcodeLiteral = Opcode::CAP_SET_DESPIN_TORQUE; :>> opcodeNumber = 2056; :>> mnemonic = "CAP_SET_DESPIN_TORQUE";
        :>> application = ApplicationName::captureControl; :>> apidClass = ApidClass::capture; :>> apid = 967;
        :>> allowedModes = (TugMode::despin); :>> criticality = CommandCriticality::critical; :>> hazardous = false;
        :>> argumentCount = 1; :>> argumentBits = 16;
        attribute torque : Real, CommandArgument { :>> minimum = 0.0; :>> maximum = 1.0; :>> widthBits = 16; }
    }
    item capLatchBody : CommandDefinition {
        doc /* Engage the body latches. */
        :>> opcodeLiteral = Opcode::CAP_LATCH_BODY; :>> opcodeNumber = 2057; :>> mnemonic = "CAP_LATCH_BODY";
        :>> application = ApplicationName::captureControl; :>> apidClass = ApidClass::capture; :>> apid = 967;
        :>> allowedModes = (TugMode::capture, TugMode::despin); :>> criticality = CommandCriticality::critical; :>> hazardous = true;
        :>> argumentCount = 1; :>> argumentBits = 8;
        attribute latchMask : Natural, CommandArgument { :>> minimum = 0.0; :>> maximum = 15.0; :>> widthBits = 8; }
    }
    item capReleaseBody : CommandDefinition {
        doc /* Release the body latches and the bag; irreversible for the mission. */
        :>> opcodeLiteral = Opcode::CAP_RELEASE_BODY; :>> opcodeNumber = 2058; :>> mnemonic = "CAP_RELEASE_BODY";
        :>> application = ApplicationName::captureControl; :>> apidClass = ApidClass::capture; :>> apid = 967;
        :>> allowedModes = (TugMode::droHold, TugMode::abortHold); :>> criticality = CommandCriticality::hazardous; :>> hazardous = true;
        :>> argumentCount = 1; :>> argumentBits = 16;
        attribute confirmKey : Natural, CommandArgument { :>> minimum = 0.0; :>> maximum = 65535.0; :>> widthBits = 16; }
    }
    item capAbortCapture : CommandDefinition {
        doc /* Abort the capture: open the bag and retreat. */
        :>> opcodeLiteral = Opcode::CAP_ABORT_CAPTURE; :>> opcodeNumber = 2059; :>> mnemonic = "CAP_ABORT_CAPTURE";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 0; :>> argumentBits = 0;
    }
    item capSetApproachRate : CommandDefinition {
        doc /* Set the closing rate limit for the final approach. */
        :>> opcodeLiteral = Opcode::CAP_SET_APPROACH_RATE; :>> opcodeNumber = 2060; :>> mnemonic = "CAP_SET_APPROACH_RATE";
        :>> application = ApplicationName::captureControl; :>> apidClass = ApidClass::capture; :>> apid = 967;
        :>> allowedModes = proximityModes; :>> criticality = CommandCriticality::critical; :>> hazardous = false;
        :>> argumentCount = 1; :>> argumentBits = 16;
        attribute rate : SpeedValue, CommandArgument { :>> minimum = 0.01; :>> maximum = 0.5; :>> widthBits = 16; }
    }
    item capEnableProximitySensors : CommandDefinition {
        doc /* Power and enable the proximity sensor suite. */
        :>> opcodeLiteral = Opcode::CAP_ENABLE_PROXIMITY_SENSORS; :>> opcodeNumber = 2061; :>> mnemonic = "CAP_ENABLE_PROXIMITY_SENSORS";
        :>> application = ApplicationName::captureControl; :>> apidClass = ApidClass::capture; :>> apid = 967;
        :>> allowedModes = allFlightModes; :>> criticality = CommandCriticality::routine; :>> hazardous = false;
        :>> argumentCount = 0; :>> argumentBits = 0;
    }
    item capDisableProximitySensors : CommandDefinition {
        doc /* Disable the proximity sensor suite. */
        :>> opcodeLiteral = Opcode::CAP_DISABLE_PROXIMITY_SENSORS; :>> opcodeNumber = 2062; :>> mnemonic = "CAP_DISABLE_PROXIMITY_SENSORS";
        :>> application = ApplicationName::captureControl; :>> apidClass = ApidClass::capture; :>> apid = 967;
        :>> allowedModes = allFlightModes; :>> criticality = CommandCriticality::routine; :>> hazardous = false;
        :>> argumentCount = 0; :>> argumentBits = 0;
    }
    item capSetContactForceLimit : CommandDefinition {
        doc /* Set the contact force at which the controller backs off. */
        :>> opcodeLiteral = Opcode::CAP_SET_CONTACT_FORCE_LIMIT; :>> opcodeNumber = 2063; :>> mnemonic = "CAP_SET_CONTACT_FORCE_LIMIT";
        :>> application = ApplicationName::captureControl; :>> apidClass = ApidClass::capture; :>> apid = 967;
        :>> allowedModes = (TugMode::proximityOperations, TugMode::capture, TugMode::despin); :>> criticality = CommandCriticality::critical; :>> hazardous = false;
        :>> argumentCount = 1; :>> argumentBits = 16;
        attribute limit : ForceValue, CommandArgument { :>> minimum = 1.0; :>> maximum = 500.0; :>> widthBits = 16; }
    }
    item capSetBodyMassEstimate : CommandDefinition {
        doc /* Load the ground estimate of the body mass into the controller. */
        :>> opcodeLiteral = Opcode::CAP_SET_BODY_MASS_ESTIMATE; :>> opcodeNumber = 2064; :>> mnemonic = "CAP_SET_BODY_MASS_ESTIMATE";
        :>> application = ApplicationName::captureControl; :>> apidClass = ApidClass::capture; :>> apid = 967;
        :>> allowedModes = allFlightModes; :>> criticality = CommandCriticality::routine; :>> hazardous = false;
        :>> argumentCount = 1; :>> argumentBits = 32;
        attribute massTonnes : Real, CommandArgument { :>> minimum = 1.0; :>> maximum = 2000.0; :>> widthBits = 32; }
    }
    item capPetalOpen1 : CommandDefinition {
        doc /* Open bag petal 1. */
        :>> opcodeLiteral = Opcode::CAP_PETAL_OPEN_1; :>> opcodeNumber = 2065; :>> mnemonic = "CAP_PETAL_OPEN_1";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 0; :>> argumentBits = 0;
    }
    item capPetalClose1 : CommandDefinition {
        doc /* Close bag petal 1. */
        :>> opcodeLiteral = Opcode::CAP_PETAL_CLOSE_1; :>> opcodeNumber = 2066; :>> mnemonic = "CAP_PETAL_CLOSE_1";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 0; :>> argumentBits = 0;
    }
    item capPetalOpen2 : CommandDefinition {
        doc /* Open bag petal 2. */
        :>> opcodeLiteral = Opcode::CAP_PETAL_OPEN_2; :>> opcodeNumber = 2067; :>> mnemonic = "CAP_PETAL_OPEN_2";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 0; :>> argumentBits = 0;
    }
    item capPetalClose2 : CommandDefinition {
        doc /* Close bag petal 2. */
        :>> opcodeLiteral = Opcode::CAP_PETAL_CLOSE_2; :>> opcodeNumber = 2068; :>> mnemonic = "CAP_PETAL_CLOSE_2";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 0; :>> argumentBits = 0;
    }
    item capPetalOpen3 : CommandDefinition {
        doc /* Open bag petal 3. */
        :>> opcodeLiteral = Opcode::CAP_PETAL_OPEN_3; :>> opcodeNumber = 2069; :>> mnemonic = "CAP_PETAL_OPEN_3";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 0; :>> argumentBits = 0;
    }
    item capPetalClose3 : CommandDefinition {
        doc /* Close bag petal 3. */
        :>> opcodeLiteral = Opcode::CAP_PETAL_CLOSE_3; :>> opcodeNumber = 2070; :>> mnemonic = "CAP_PETAL_CLOSE_3";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 0; :>> argumentBits = 0;
    }
    item capPetalOpen4 : CommandDefinition {
        doc /* Open bag petal 4. */
        :>> opcodeLiteral = Opcode::CAP_PETAL_OPEN_4; :>> opcodeNumber = 2071; :>> mnemonic = "CAP_PETAL_OPEN_4";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 0; :>> argumentBits = 0;
    }
    item capPetalClose4 : CommandDefinition {
        doc /* Close bag petal 4. */
        :>> opcodeLiteral = Opcode::CAP_PETAL_CLOSE_4; :>> opcodeNumber = 2072; :>> mnemonic = "CAP_PETAL_CLOSE_4";
        :>> application = ApplicationName::captureControl; :>> apidClass = ApidClass::capture; :>> apid = 967;
        :>> allowedModes = (TugMode::proximityOperations, TugMode::capture, TugMode::despin); :>> criticality = CommandCriticality::critical; :>> hazardous = true;
        :>> argumentCount = 0; :>> argumentBits = 0;
    }
    item autLoadSequence : CommandDefinition {
        doc /* Load a command sequence into an engine. */
        :>> opcodeLiteral = Opcode::AUT_LOAD_SEQUENCE; :>> opcodeNumber = 2305; :>> mnemonic = "AUT_LOAD_SEQUENCE";
        :>> application = ApplicationName::autonomy; :>> apidClass = ApidClass::guidance; :>> apid = 968;
        :>> allowedModes = allFlightModes; :>> criticality = CommandCriticality::routine; :>> hazardous = false;
        :>> argumentCount = 3; :>> argumentBits = 40;
        attribute engine : Natural, CommandArgument { :>> minimum = 0.0; :>> maximum = 3.0; :>> widthBits = 8; }
        attribute sequenceId : Natural, CommandArgument { :>> minimum = 0.0; :>> maximum = 65535.0; :>> widthBits = 16; }
        attribute byteCount : Natural, CommandArgument { :>> minimum = 1.0; :>> maximum = 4096.0; :>> widthBits = 16; }
    }
    item autStartSequence : CommandDefinition {
        doc /* Start the sequence loaded in an engine. */
        :>> opcodeLiteral = Opcode::AUT_START_SEQUENCE; :>> opcodeNumber = 2306; :>> mnemonic = "AUT_START_SEQUENCE";
        :>> application = ApplicationName::autonomy; :>> apidClass = ApidClass::guidance; :>> apid = 968;
        :>> allowedModes = allFlightModes; :>> criticality = CommandCriticality::critical; :>> hazardous = false;
        :>> argumentCount = 1; :>> argumentBits = 8;
        attribute engine : Natural, CommandArgument { :>> minimum = 0.0; :>> maximum = 3.0; :>> widthBits = 8; }
    }
    item autStopSequence : CommandDefinition {
        doc /* Stop and unload the sequence in an engine. */
        :>> opcodeLiteral = Opcode::AUT_STOP_SEQUENCE; :>> opcodeNumber = 2307; :>> mnemonic = "AUT_STOP_SEQUENCE";
        :>> application = ApplicationName::autonomy; :>> apidClass = ApidClass::guidance; :>> apid = 968;
        :>> allowedModes = allFlightModes; :>> criticality = CommandCriticality::critical; :>> hazardous = false;
        :>> argumentCount = 1; :>> argumentBits = 8;
        attribute engine : Natural, CommandArgument { :>> minimum = 0.0; :>> maximum = 3.0; :>> widthBits = 8; }
    }
    item autPauseSequence : CommandDefinition {
        doc /* Pause the sequence in an engine. */
        :>> opcodeLiteral = Opcode::AUT_PAUSE_SEQUENCE; :>> opcodeNumber = 2308; :>> mnemonic = "AUT_PAUSE_SEQUENCE";
        :>> application = ApplicationName::autonomy; :>> apidClass = ApidClass::guidance; :>> apid = 968;
        :>> allowedModes = allFlightModes; :>> criticality = CommandCriticality::routine; :>> hazardous = false;
        :>> argumentCount = 1; :>> argumentBits = 8;
        attribute engine : Natural, CommandArgument { :>> minimum = 0.0; :>> maximum = 3.0; :>> widthBits = 8; }
    }
    item autResumeSequence : CommandDefinition {
        doc /* Resume a paused sequence. */
        :>> opcodeLiteral = Opcode::AUT_RESUME_SEQUENCE; :>> opcodeNumber = 2309; :>> mnemonic = "AUT_RESUME_SEQUENCE";
        :>> application = ApplicationName::autonomy; :>> apidClass = ApidClass::guidance; :>> apid = 968;
        :>> allowedModes = allFlightModes; :>> criticality = CommandCriticality::routine; :>> hazardous = false;
        :>> argumentCount = 1; :>> argumentBits = 8;
        attribute engine : Natural, CommandArgument { :>> minimum = 0.0; :>> maximum = 3.0; :>> widthBits = 8; }
    }
    item autSetSequenceParameter : CommandDefinition {
        doc /* Set a sequence parameter by index. */
        :>> opcodeLiteral = Opcode::AUT_SET_SEQUENCE_PARAMETER; :>> opcodeNumber = 2310; :>> mnemonic = "AUT_SET_SEQUENCE_PARAMETER";
        :>> application = ApplicationName::autonomy; :>> apidClass = ApidClass::guidance; :>> apid = 968;
        :>> allowedModes = allFlightModes; :>> criticality = CommandCriticality::routine; :>> hazardous = false;
        :>> argumentCount = 3; :>> argumentBits = 48;
        attribute engine : Natural, CommandArgument { :>> minimum = 0.0; :>> maximum = 3.0; :>> widthBits = 8; }
        attribute index : Natural, CommandArgument { :>> minimum = 0.0; :>> maximum = 255.0; :>> widthBits = 8; }
        attribute value : Real, CommandArgument { :>> minimum = -1000000000.0; :>> maximum = 1000000000.0; :>> widthBits = 32; }
    }
    item autEnableAutonomy : CommandDefinition {
        doc /* Enable on-board autonomy at the given level. */
        :>> opcodeLiteral = Opcode::AUT_ENABLE_AUTONOMY; :>> opcodeNumber = 2311; :>> mnemonic = "AUT_ENABLE_AUTONOMY";
        :>> application = ApplicationName::autonomy; :>> apidClass = ApidClass::guidance; :>> apid = 968;
        :>> allowedModes = allFlightModes; :>> criticality = CommandCriticality::critical; :>> hazardous = false;
        :>> argumentCount = 1; :>> argumentBits = 8;
        attribute level : Natural, CommandArgument { :>> minimum = 0.0; :>> maximum = 3.0; :>> widthBits = 8; }
    }
    item autDisableAutonomy : CommandDefinition {
        doc /* Disable on-board autonomy; sequences run but rules do not fire. */
        :>> opcodeLiteral = Opcode::AUT_DISABLE_AUTONOMY; :>> opcodeNumber = 2312; :>> mnemonic = "AUT_DISABLE_AUTONOMY";
        :>> application = ApplicationName::autonomy; :>> apidClass = ApidClass::guidance; :>> apid = 968;
        :>> allowedModes = allFlightModes; :>> criticality = CommandCriticality::critical; :>> hazardous = false;
        :>> argumentCount = 0; :>> argumentBits = 0;
    }
    item autSetRuleEnable : CommandDefinition {
        doc /* Enable or disable an autonomy rule. */
        :>> opcodeLiteral = Opcode::AUT_SET_RULE_ENABLE; :>> opcodeNumber = 2313; :>> mnemonic = "AUT_SET_RULE_ENABLE";
        :>> application = ApplicationName::autonomy; :>> apidClass = ApidClass::guidance; :>> apid = 968;
        :>> allowedModes = allFlightModes; :>> criticality = CommandCriticality::critical; :>> hazardous = false;
        :>> argumentCount = 2; :>> argumentBits = 16;
        attribute rule : Natural, CommandArgument { :>> minimum = 0.0; :>> maximum = 15.0; :>> widthBits = 8; }
        attribute enabled : Natural, CommandArgument { :>> minimum = 0.0; :>> maximum = 1.0; :>> widthBits = 8; }
    }
    item autClearRuleHistory : CommandDefinition {
        doc /* Clear the rule firing history. */
        :>> opcodeLiteral = Opcode::AUT_CLEAR_RULE_HISTORY; :>> opcodeNumber = 2314; :>> mnemonic = "AUT_CLEAR_RULE_HISTORY";
        :>> application = ApplicationName::autonomy; :>> apidClass = ApidClass::guidance; :>> apid = 968;
        :>> allowedModes = allFlightModes; :>> criticality = CommandCriticality::routine; :>> hazardous = false;
        :>> argumentCount = 0; :>> argumentBits = 0;
    }
    item autSetWaypoint : CommandDefinition {
        doc /* Add a proximity-operations waypoint. */
        :>> opcodeLiteral = Opcode::AUT_SET_WAYPOINT; :>> opcodeNumber = 2315; :>> mnemonic = "AUT_SET_WAYPOINT";
        :>> application = ApplicationName::autonomy; :>> apidClass = ApidClass::guidance; :>> apid = 968;
        :>> allowedModes = proximityModes; :>> criticality = CommandCriticality::critical; :>> hazardous = false;
        :>> argumentCount = 3; :>> argumentBits = 72;
        attribute index : Natural, CommandArgument { :>> minimum = 0.0; :>> maximum = 31.0; :>> widthBits = 8; }
        attribute rangeMetres : LengthValue, CommandArgument { :>> minimum = 50.0; :>> maximum = 5000.0; :>> widthBits = 32; }
        attribute holdTime : DurationValue, CommandArgument { :>> minimum = 0.0; :>> maximum = 86400.0; :>> widthBits = 32; }
    }
    item autClearWaypoints : CommandDefinition {
        doc /* Clear the waypoint list. */
        :>> opcodeLiteral = Opcode::AUT_CLEAR_WAYPOINTS; :>> opcodeNumber = 2316; :>> mnemonic = "AUT_CLEAR_WAYPOINTS";
        :>> application = ApplicationName::autonomy; :>> apidClass = ApidClass::guidance; :>> apid = 968;
        :>> allowedModes = allFlightModes; :>> criticality = CommandCriticality::critical; :>> hazardous = false;
        :>> argumentCount = 0; :>> argumentBits = 0;
    }
    item autSetPlanHorizon : CommandDefinition {
        doc /* Set the planning horizon of the autonomy executive. */
        :>> opcodeLiteral = Opcode::AUT_SET_PLAN_HORIZON; :>> opcodeNumber = 2317; :>> mnemonic = "AUT_SET_PLAN_HORIZON";
        :>> application = ApplicationName::autonomy; :>> apidClass = ApidClass::guidance; :>> apid = 968;
        :>> allowedModes = allFlightModes; :>> criticality = CommandCriticality::routine; :>> hazardous = false;
        :>> argumentCount = 1; :>> argumentBits = 32;
        attribute horizon : DurationValue, CommandArgument { :>> minimum = 3600.0; :>> maximum = 604800.0; :>> widthBits = 32; }
    }
    item autEngineEnable1 : CommandDefinition {
        doc /* Enable sequence engine 1. */
        :>> opcodeLiteral = Opcode::AUT_ENGINE_ENABLE_1; :>> opcodeNumber = 2318; :>> mnemonic = "AUT_ENGINE_ENABLE_1";
        :>> application = ApplicationName::autonomy; :>> apidClass = ApidClass::guidance; :>> apid = 968;
        :>> allowedModes = allFlightModes; :>> criticality = CommandCriticality::routine; :>> hazardous = false;
        :>> argumentCount = 0; :>> argumentBits = 0;
    }
    item autEngineDisable1 : CommandDefinition {
        doc /* Disable sequence engine 1. */
        :>> opcodeLiteral = Opcode::AUT_ENGINE_DISABLE_1; :>> opcodeNumber = 2319; :>> mnemonic = "AUT_ENGINE_DISABLE_1";
        :>> application = ApplicationName::autonomy; :>> apidClass = ApidClass::guidance; :>> apid = 968;
        :>> allowedModes = allFlightModes; :>> criticality = CommandCriticality::routine; :>> hazardous = false;
        :>> argumentCount = 0; :>> argumentBits = 0;
    }
    item autEngineEnable2 : CommandDefinition {
        doc /* Enable sequence engine 2. */
        :>> opcodeLiteral = Opcode::AUT_ENGINE_ENABLE_2; :>> opcodeNumber = 2320; :>> mnemonic = "AUT_ENGINE_ENABLE_2";
        :>> application = ApplicationName::autonomy; :>> apidClass = ApidClass::guidance; :>> apid = 968;
        :>> allowedModes = allFlightModes; :>> criticality = CommandCriticality::routine; :>> hazardous = false;
        :>> argumentCount = 0; :>> argumentBits = 0;
    }
    item autEngineDisable2 : CommandDefinition {
        doc /* Disable sequence engine 2. */
        :>> opcodeLiteral = Opcode::AUT_ENGINE_DISABLE_2; :>> opcodeNumber = 2321; :>> mnemonic = "AUT_ENGINE_DISABLE_2";
        :>> application = ApplicationName::autonomy; :>> apidClass = ApidClass::guidance; :>> apid = 968;
        :>> allowedModes = allFlightModes; :>> criticality = CommandCriticality::routine; :>> hazardous = false;
        :>> argumentCount = 0; :>> argumentBits = 0;
    }
    item autEngineEnable3 : CommandDefinition {
        doc /* Enable sequence engine 3. */
        :>> opcodeLiteral = Opcode::AUT_ENGINE_ENABLE_3; :>> opcodeNumber = 2322; :>> mnemonic = "AUT_ENGINE_ENABLE_3";
        :>> application = ApplicationName::autonomy; :>> apidClass = ApidClass::guidance; :>> apid = 968;
        :>> allowedModes = allFlightModes; :>> criticality = CommandCriticality::routine; :>> hazardous = false;
        :>> argumentCount = 0; :>> argumentBits = 0;
    }
    item autEngineDisable3 : CommandDefinition {
        doc /* Disable sequence engine 3. */
        :>> opcodeLiteral = Opcode::AUT_ENGINE_DISABLE_3; :>> opcodeNumber = 2323; :>> mnemonic = "AUT_ENGINE_DISABLE_3";
        :>> application = ApplicationName::autonomy; :>> apidClass = ApidClass::guidance; :>> apid = 968;
        :>> allowedModes = allFlightModes; :>> criticality = CommandCriticality::routine; :>> hazardous = false;
        :>> argumentCount = 0; :>> argumentBits = 0;
    }
    item autEngineEnable4 : CommandDefinition {
        doc /* Enable sequence engine 4. */
        :>> opcodeLiteral = Opcode::AUT_ENGINE_ENABLE_4; :>> opcodeNumber = 2324; :>> mnemonic = "AUT_ENGINE_ENABLE_4";
        :>> application = ApplicationName::autonomy; :>> apidClass = ApidClass::guidance; :>> apid = 968;
        :>> allowedModes = allFlightModes; :>> criticality = CommandCriticality::routine; :>> hazardous = false;
        :>> argumentCount = 0; :>> argumentBits = 0;
    }
    item autEngineDisable4 : CommandDefinition {
        doc /* Disable sequence engine 4. */
        :>> opcodeLiteral = Opcode::AUT_ENGINE_DISABLE_4; :>> opcodeNumber = 2325; :>> mnemonic = "AUT_ENGINE_DISABLE_4";
        :>> application = ApplicationName::autonomy; :>> apidClass = ApidClass::guidance; :>> apid = 968;
        :>> allowedModes = allFlightModes; :>> criticality = CommandCriticality::routine; :>> hazardous = false;
        :>> argumentCount = 0; :>> argumentBits = 0;
    }
    item fdrEnableMonitor : CommandDefinition {
        doc /* Enable a fault monitor. */
        :>> opcodeLiteral = Opcode::FDR_ENABLE_MONITOR; :>> opcodeNumber = 2561; :>> mnemonic = "FDR_ENABLE_MONITOR";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute monitor : Natural, CommandArgument { :>> minimum = 0.0; :>> maximum = 47.0; :>> widthBits = 8; }
    }
    item fdrDisableMonitor : CommandDefinition {
        doc /* Disable a fault monitor. */
        :>> opcodeLiteral = Opcode::FDR_DISABLE_MONITOR; :>> opcodeNumber = 2562; :>> mnemonic = "FDR_DISABLE_MONITOR";
        :>> application = ApplicationName::fdir; :>> apidClass = ApidClass::housekeeping; :>> apid = 969;
        :>> allowedModes = allFlightModes; :>> criticality = CommandCriticality::critical; :>> hazardous = true;
        :>> argumentCount = 1; :>> argumentBits = 8;
        attribute monitor : Natural, CommandArgument { :>> minimum = 0.0; :>> maximum = 47.0; :>> widthBits = 8; }
    }
    item fdrSetLimit : CommandDefinition {
        doc /* Set the red and yellow limits of a monitored point. */
        :>> opcodeLiteral = Opcode::FDR_SET_LIMIT; :>> opcodeNumber = 2563; :>> mnemonic = "FDR_SET_LIMIT";
        :>> application = ApplicationName::fdir; :>> apidClass = ApidClass::housekeeping; :>> apid = 969;
        :>> allowedModes = allFlightModes; :>> criticality = CommandCriticality::critical; :>> hazardous = false;
        :>> argumentCount = 5; :>> argumentBits = 144;
        attribute pointId : Natural, CommandArgument { :>> minimum = 0.0; :>> maximum = 65535.0; :>> widthBits = 16; }
        attribute redLow : Real, CommandArgument { :>> minimum = -1000000000.0; :>> maximum = 1000000000.0; :>> widthBits = 32; }
        attribute yellowLow : Real, CommandArgument { :>> minimum = -1000000000.0; :>> maximum = 1000000000.0; :>> widthBits = 32; }
        attribute yellowHigh : Real, CommandArgument { :>> minimum = -1000000000.0; :>> maximum = 1000000000.0; :>> widthBits = 32; }
        attribute redHigh : Real, CommandArgument { :>> minimum = -1000000000.0; :>> maximum = 1000000000.0; :>> widthBits = 32; }
    }
    item fdrResetLimit : CommandDefinition {
        doc /* Return a monitored point to its table limits. */
        :>> opcodeLiteral = Opcode::FDR_RESET_LIMIT; :>> opcodeNumber = 2564; :>> mnemonic = "FDR_RESET_LIMIT";
        :>> application = ApplicationName::fdir; :>> apidClass = ApidClass::housekeeping; :>> apid = 969;
        :>> allowedModes = allFlightModes; :>> criticality = CommandCriticality::routine; :>> hazardous = false;
        :>> argumentCount = 1; :>> argumentBits = 16;
        attribute pointId : Natural, CommandArgument { :>> minimum = 0.0; :>> maximum = 65535.0; :>> widthBits = 16; }
    }
    item fdrClearFault : CommandDefinition {
        doc /* Clear a latched fault. */
        :>> opcodeLiteral = Opcode::FDR_CLEAR_FAULT; :>> opcodeNumber = 2565; :>> mnemonic = "FDR_CLEAR_FAULT";
        :>> application = ApplicationName::fdir; :>> apidClass = ApidClass::housekeeping; :>> apid = 969;
        :>> allowedModes = allFlightModes; :>> criticality = CommandCriticality::critical; :>> hazardous = false;
        :>> argumentCount = 1; :>> argumentBits = 16;
        attribute faultId : Natural, CommandArgument { :>> minimum = 0.0; :>> maximum = 65535.0; :>> widthBits = 16; }
    }
    item fdrAcknowledgeFault : CommandDefinition {
        doc /* Acknowledge a fault so its response may re-arm. */
        :>> opcodeLiteral = Opcode::FDR_ACKNOWLEDGE_FAULT; :>> opcodeNumber = 2566; :>> mnemonic = "FDR_ACKNOWLEDGE_FAULT";
        :>> application = ApplicationName::fdir; :>> apidClass = ApidClass::housekeeping; :>> apid = 969;
        :>> allowedModes = allFlightModes; :>> criticality = CommandCriticality::routine; :>> hazardous = false;
        :>> argumentCount = 1; :>> argumentBits = 16;
        attribute faultId : Natural, CommandArgument { :>> minimum = 0.0; :>> maximum = 65535.0; :>> widthBits = 16; }
    }
    item fdrMaskResponse : CommandDefinition {
        doc /* Mask a fault response. */
        :>> opcodeLiteral = Opcode::FDR_MASK_RESPONSE; :>> opcodeNumber = 2567; :>> mnemonic = "FDR_MASK_RESPONSE";
        :>> application = ApplicationName::fdir; :>> apidClass = ApidClass::housekeeping; :>> apid = 969;
        :>> allowedModes = allFlightModes; :>> criticality = CommandCriticality::critical; :>> hazardous = true;
        :>> argumentCount = 1; :>> argumentBits = 8;
        attribute response : Natural, CommandArgument { :>> minimum = 0.0; :>> maximum = 4.0; :>> widthBits = 8; }
    }
    item fdrUnmaskResponse : CommandDefinition {
        doc /* Unmask a fault response. */
        :>> opcodeLiteral = Opcode::FDR_UNMASK_RESPONSE; :>> opcodeNumber = 2568; :>> mnemonic = "FDR_UNMASK_RESPONSE";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrForceSafeMode : CommandDefinition {
        doc /* Command safe mode directly. */
        :>> opcodeLiteral = Opcode::FDR_FORCE_SAFE_MODE; :>> opcodeNumber = 2569; :>> mnemonic = "FDR_FORCE_SAFE_MODE";
        :>> application = ApplicationName::fdir; :>> apidClass = ApidClass::housekeeping; :>> apid = 969;
        :>> allowedModes = allFlightModes; :>> criticality = CommandCriticality::critical; :>> hazardous = true;
        :>> argumentCount = 0; :>> argumentBits = 0;
    }
    item fdrSetCommandLossTimer : CommandDefinition {
        doc /* Set the command-loss timer that calls safe mode when no command arrives. */
        :>> opcodeLiteral = Opcode::FDR_SET_COMMAND_LOSS_TIMER; :>> opcodeNumber = 2570; :>> mnemonic = "FDR_SET_COMMAND_LOSS_TIMER";
        :>> application = ApplicationName::fdir; :>> apidClass = ApidClass::housekeeping; :>> apid = 969;
        :>> allowedModes = allFlightModes; :>> criticality = CommandCriticality::critical; :>> hazardous = false;
        :>> argumentCount = 1; :>> argumentBits = 32;
        attribute timeout : DurationValue, CommandArgument { :>> minimum = 3600.0; :>> maximum = 2592000.0; :>> widthBits = 32; }
    }
    item fdrResetCommandLossTimer : CommandDefinition {
        doc /* Restart the command-loss timer. */
        :>> opcodeLiteral = Opcode::FDR_RESET_COMMAND_LOSS_TIMER; :>> opcodeNumber = 2571; :>> mnemonic = "FDR_RESET_COMMAND_LOSS_TIMER";
        :>> application = ApplicationName::fdir; :>> apidClass = ApidClass::housekeeping; :>> apid = 969;
        :>> allowedModes = allFlightModes; :>> criticality = CommandCriticality::routine; :>> hazardous = false;
        :>> argumentCount = 0; :>> argumentBits = 0;
    }
    item fdrAbortToRetreat : CommandDefinition {
        doc /* Abort proximity operations and retreat to the hold point. */
        :>> opcodeLiteral = Opcode::FDR_ABORT_TO_RETREAT; :>> opcodeNumber = 2572; :>> mnemonic = "FDR_ABORT_TO_RETREAT";
        :>> application = ApplicationName::fdir; :>> apidClass = ApidClass::housekeeping; :>> apid = 969;
        :>> allowedModes = (TugMode::proximityOperations, TugMode::capture, TugMode::despin); :>> criticality = CommandCriticality::critical; :>> hazardous = true;
        :>> argumentCount = 0; :>> argumentBits = 0;
    }
    item fdrSetFlameoutRetries : CommandDefinition {
        doc /* Set the thruster restarts tried before a switchover. */
        :>> opcodeLiteral = Opcode::FDR_SET_FLAMEOUT_RETRIES; :>> opcodeNumber = 2573; :>> mnemonic = "FDR_SET_FLAMEOUT_RETRIES";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute retries : Natural, CommandArgument { :>> minimum = 0.0; :>> maximum = 5.0; :>> widthBits = 8; }
    }
    item fdrSetBatteryLowFraction : CommandDefinition {
        doc /* Set the state of charge at which load shedding starts. */
        :>> opcodeLiteral = Opcode::FDR_SET_BATTERY_LOW_FRACTION; :>> opcodeNumber = 2574; :>> mnemonic = "FDR_SET_BATTERY_LOW_FRACTION";
        :>> application = ApplicationName::fdir; :>> apidClass = ApidClass::housekeeping; :>> apid = 969;
        :>> allowedModes = allFlightModes; :>> criticality = CommandCriticality::critical; :>> hazardous = false;
        :>> argumentCount = 1; :>> argumentBits = 16;
        attribute fraction : Real, CommandArgument { :>> minimum = 0.1; :>> maximum = 0.6; :>> widthBits = 16; }
    }
    item fdrSetImpactProbabilityLimit : CommandDefinition {
        doc /* Set the Earth impact probability above which the supervisor aborts. */
        :>> opcodeLiteral = Opcode::FDR_SET_IMPACT_PROBABILITY_LIMIT; :>> opcodeNumber = 2575; :>> mnemonic = "FDR_SET_IMPACT_PROBABILITY_LIMIT";
        :>> application = ApplicationName::fdir; :>> apidClass = ApidClass::housekeeping; :>> apid = 969;
        :>> allowedModes = allFlightModes; :>> criticality = CommandCriticality::critical; :>> hazardous = false;
        :>> argumentCount = 1; :>> argumentBits = 32;
        attribute limit : Real, CommandArgument { :>> minimum = 1e-07; :>> maximum = 0.001; :>> widthBits = 32; }
    }
    item fdrSetExclusionRadius : CommandDefinition {
        doc /* Set the Earth exclusion radius. */
        :>> opcodeLiteral = Opcode::FDR_SET_EXCLUSION_RADIUS; :>> opcodeNumber = 2576; :>> mnemonic = "FDR_SET_EXCLUSION_RADIUS";
        :>> application = ApplicationName::fdir; :>> apidClass = ApidClass::housekeeping; :>> apid = 969;
        :>> allowedModes = (TugMode::earlyOperations, TugMode::coast, TugMode::droHold, TugMode::safe); :>> criticality = CommandCriticality::critical; :>> hazardous = false;
        :>> argumentCount = 1; :>> argumentBits = 32;
        attribute radius : LengthValue, CommandArgument { :>> minimum = 10000000.0; :>> maximum = 100000000.0; :>> widthBits = 32; }
    }
    item fdrMonitorResponse01 : CommandDefinition {
        doc /* Set the response of monitor 1. */
        :>> opcodeLiteral = Opcode::FDR_MONITOR_RESPONSE_01; :>> opcodeNumber = 2577; :>> mnemonic = "FDR_MONITOR_RESPONSE_01";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse02 : CommandDefinition {
        doc /* Set the response of monitor 2. */
        :>> opcodeLiteral = Opcode::FDR_MONITOR_RESPONSE_02; :>> opcodeNumber = 2578; :>> mnemonic = "FDR_MONITOR_RESPONSE_02";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse03 : CommandDefinition {
        doc /* Set the response of monitor 3. */
        :>> opcodeLiteral = Opcode::FDR_MONITOR_RESPONSE_03; :>> opcodeNumber = 2579; :>> mnemonic = "FDR_MONITOR_RESPONSE_03";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse04 : CommandDefinition {
        doc /* Set the response of monitor 4. */
        :>> opcodeLiteral = Opcode::FDR_MONITOR_RESPONSE_04; :>> opcodeNumber = 2580; :>> mnemonic = "FDR_MONITOR_RESPONSE_04";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse05 : CommandDefinition {
        doc /* Set the response of monitor 5. */
        :>> opcodeLiteral = Opcode::FDR_MONITOR_RESPONSE_05; :>> opcodeNumber = 2581; :>> mnemonic = "FDR_MONITOR_RESPONSE_05";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse06 : CommandDefinition {
        doc /* Set the response of monitor 6. */
        :>> opcodeLiteral = Opcode::FDR_MONITOR_RESPONSE_06; :>> opcodeNumber = 2582; :>> mnemonic = "FDR_MONITOR_RESPONSE_06";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse07 : CommandDefinition {
        doc /* Set the response of monitor 7. */
        :>> opcodeLiteral = Opcode::FDR_MONITOR_RESPONSE_07; :>> opcodeNumber = 2583; :>> mnemonic = "FDR_MONITOR_RESPONSE_07";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse08 : CommandDefinition {
        doc /* Set the response of monitor 8. */
        :>> opcodeLiteral = Opcode::FDR_MONITOR_RESPONSE_08; :>> opcodeNumber = 2584; :>> mnemonic = "FDR_MONITOR_RESPONSE_08";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse09 : CommandDefinition {
        doc /* Set the response of monitor 9. */
        :>> opcodeLiteral = Opcode::FDR_MONITOR_RESPONSE_09; :>> opcodeNumber = 2585; :>> mnemonic = "FDR_MONITOR_RESPONSE_09";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse10 : CommandDefinition {
        doc /* Set the response of monitor 10. */
        :>> opcodeLiteral = Opcode::FDR_MONITOR_RESPONSE_10; :>> opcodeNumber = 2586; :>> mnemonic = "FDR_MONITOR_RESPONSE_10";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse11 : CommandDefinition {
        doc /* Set the response of monitor 11. */
        :>> opcodeLiteral = Opcode::FDR_MONITOR_RESPONSE_11; :>> opcodeNumber = 2587; :>> mnemonic = "FDR_MONITOR_RESPONSE_11";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item fdrMonitorResponse12 : CommandDefinition {
        doc /* Set the response of monitor 12. */
        :>> opcodeLiteral = Opcode::FDR_MONITOR_RESPONSE_12; :>> opcodeNumber = 2588; :>> mnemonic = "FDR_MONITOR_RESPONSE_12";
        :>> application = ApplicationName::fdir; :>> apidClass = ApidClass::housekeeping; :>> apid = 969;
        :>> allowedModes = allFlightModes; :>> criticality = CommandCriticality::critical; :>> hazardous = false;
        :>> argumentCount = 1; :>> argumentBits = 8;
        attribute response : Natural, CommandArgument { :>> minimum = 0.0; :>> maximum = 4.0; :>> widthBits = 8; }
    }
    item modSetMode : CommandDefinition {
        doc /* Transition the tug to a commanded mode. */
        :>> opcodeLiteral = Opcode::MOD_SET_MODE; :>> opcodeNumber = 2817; :>> mnemonic = "MOD_SET_MODE";
        :>> application = ApplicationName::modeManagement; :>> apidClass = ApidClass::housekeeping; :>> apid = 970;
        :>> allowedModes = allFlightModes; :>> criticality = CommandCriticality::critical; :>> hazardous = true;
        :>> argumentCount = 1; :>> argumentBits = 8;
        attribute mode : Natural, CommandArgument { :>> minimum = 0.0; :>> maximum = 15.0; :>> widthBits = 8; }
    }
    item modConfirmMode : CommandDefinition {
        doc /* Confirm a pending two-step mode transition. */
        :>> opcodeLiteral = Opcode::MOD_CONFIRM_MODE; :>> opcodeNumber = 2818; :>> mnemonic = "MOD_CONFIRM_MODE";
        :>> application = ApplicationName::modeManagement; :>> apidClass = ApidClass::housekeeping; :>> apid = 970;
        :>> allowedModes = allFlightModes; :>> criticality = CommandCriticality::critical; :>> hazardous = false;
        :>> argumentCount = 2; :>> argumentBits = 24;
        attribute mode : Natural, CommandArgument { :>> minimum = 0.0; :>> maximum = 15.0; :>> widthBits = 8; }
        attribute confirmKey : Natural, CommandArgument { :>> minimum = 0.0; :>> maximum = 65535.0; :>> widthBits = 16; }
    }
    item modCancelPendingMode : CommandDefinition {
        doc /* Cancel a pending two-step mode transition. */
        :>> opcodeLiteral = Opcode::MOD_CANCEL_PENDING_MODE; :>> opcodeNumber = 2819; :>> mnemonic = "MOD_CANCEL_PENDING_MODE";
        :>> application = ApplicationName::modeManagement; :>> apidClass = ApidClass::housekeeping; :>> apid = 970;
        :>> allowedModes = allFlightModes; :>> criticality = CommandCriticality::routine; :>> hazardous = false;
        :>> argumentCount = 0; :>> argumentBits = 0;
    }
    item modLoadModeTable : CommandDefinition {
        doc /* Load the mode × subsystem table. */
        :>> opcodeLiteral = Opcode::MOD_LOAD_MODE_TABLE; :>> opcodeNumber = 2820; :>> mnemonic = "MOD_LOAD_MODE_TABLE";
        :>> application = ApplicationName::modeManagement; :>> apidClass = ApidClass::housekeeping; :>> apid = 970;
        :>> allowedModes = (TugMode::earlyOperations, TugMode::coast, TugMode::droHold, TugMode::safe); :>> criticality = CommandCriticality::critical; :>> hazardous = false;
        :>> argumentCount = 1; :>> argumentBits = 8;
        attribute tableId : Natural, CommandArgument { :>> minimum = 0.0; :>> maximum = 11.0; :>> widthBits = 8; }
    }
    item modEnableAutoTransition : CommandDefinition {
        doc /* Allow on-board events to drive mode transitions. */
        :>> opcodeLiteral = Opcode::MOD_ENABLE_AUTO_TRANSITION; :>> opcodeNumber = 2821; :>> mnemonic = "MOD_ENABLE_AUTO_TRANSITION";
        :>> application = ApplicationName::modeManagement; :>> apidClass = ApidClass::housekeeping; :>> apid = 970;
        :>> allowedModes = allFlightModes; :>> criticality = CommandCriticality::critical; :>> hazardous = false;
        :>> argumentCount = 0; :>> argumentBits = 0;
    }
    item modDisableAutoTransition : CommandDefinition {
        doc /* Only ground commands may drive mode transitions. */
        :>> opcodeLiteral = Opcode::MOD_DISABLE_AUTO_TRANSITION; :>> opcodeNumber = 2822; :>> mnemonic = "MOD_DISABLE_AUTO_TRANSITION";
        :>> application = ApplicationName::modeManagement; :>> apidClass = ApidClass::housekeeping; :>> apid = 970;
        :>> allowedModes = allFlightModes; :>> criticality = CommandCriticality::critical; :>> hazardous = false;
        :>> argumentCount = 0; :>> argumentBits = 0;
    }
    item modHoldMode : CommandDefinition {
        doc /* Hold the current mode against events. */
        :>> opcodeLiteral = Opcode::MOD_HOLD_MODE; :>> opcodeNumber = 2823; :>> mnemonic = "MOD_HOLD_MODE";
        :>> application = ApplicationName::modeManagement; :>> apidClass = ApidClass::housekeeping; :>> apid = 970;
        :>> allowedModes = allFlightModes; :>> criticality = CommandCriticality::routine; :>> hazardous = false;
        :>> argumentCount = 0; :>> argumentBits = 0;
    }
    item modResumeMode : CommandDefinition {
        doc /* Release a mode hold. */
        :>> opcodeLiteral = Opcode::MOD_RESUME_MODE; :>> opcodeNumber = 2824; :>> mnemonic = "MOD_RESUME_MODE";
        :>> application = ApplicationName::modeManagement; :>> apidClass = ApidClass::housekeeping; :>> apid = 970;
        :>> allowedModes = allFlightModes; :>> criticality = CommandCriticality::routine; :>> hazardous = false;
        :>> argumentCount = 0; :>> argumentBits = 0;
    }
    item modSetTransitionTimeout : CommandDefinition {
        doc /* Set the time a transition may take before it is declared failed. */
        :>> opcodeLiteral = Opcode::MOD_SET_TRANSITION_TIMEOUT; :>> opcodeNumber = 2825; :>> mnemonic = "MOD_SET_TRANSITION_TIMEOUT";
        :>> application = ApplicationName::modeManagement; :>> apidClass = ApidClass::housekeeping; :>> apid = 970;
        :>> allowedModes = allFlightModes; :>> criticality = CommandCriticality::routine; :>> hazardous = false;
        :>> argumentCount = 1; :>> argumentBits = 32;
        attribute timeout : DurationValue, CommandArgument { :>> minimum = 1.0; :>> maximum = 3600.0; :>> widthBits = 32; }
    }
    item pbuLoadTable : CommandDefinition {
        doc /* Load a parameter table into the staging buffer. */
        :>> opcodeLiteral = Opcode::PBU_LOAD_TABLE; :>> opcodeNumber = 3073; :>> mnemonic = "PBU_LOAD_TABLE";
        :>> application = ApplicationName::parameterBootUpdate; :>> apidClass = ApidClass::housekeeping; :>> apid = 971;
        :>> allowedModes = allFlightModes; :>> criticality = CommandCriticality::critical; :>> hazardous = false;
        :>> argumentCount = 2; :>> argumentBits = 40;
        attribute tableId : Natural, CommandArgument { :>> minimum = 0.0; :>> maximum = 11.0; :>> widthBits = 8; }
        attribute byteCount : Natural, CommandArgument { :>> minimum = 1.0; :>> maximum = 65536.0; :>> widthBits = 32; }
    }
    item pbuDumpTable : CommandDefinition {
        doc /* Downlink a parameter table. */
        :>> opcodeLiteral = Opcode::PBU_DUMP_TABLE; :>> opcodeNumber = 3074; :>> mnemonic = "PBU_DUMP_TABLE";
        :>> application = ApplicationName::parameterBootUpdate; :>> apidClass = ApidClass::housekeeping; :>> apid = 971;
        :>> allowedModes = allFlightModes; :>> criticality = CommandCriticality::routine; :>> hazardous = false;
        :>> argumentCount = 1; :>> argumentBits = 8;
        attribute tableId : Natural, CommandArgument { :>> minimum = 0.0; :>> maximum = 11.0; :>> widthBits = 8; }
    }
    item pbuActivateTable : CommandDefinition {
        doc /* Activate a staged table after validation. */
        :>> opcodeLiteral = Opcode::PBU_ACTIVATE_TABLE; :>> opcodeNumber = 3075; :>> mnemonic = "PBU_ACTIVATE_TABLE";
        :>> application = ApplicationName::parameterBootUpdate; :>> apidClass = ApidClass::housekeeping; :>> apid = 971;
        :>> allowedModes = allFlightModes; :>> criticality = CommandCriticality::critical; :>> hazardous = true;
        :>> argumentCount = 2; :>> argumentBits = 40;
        attribute tableId : Natural, CommandArgument { :>> minimum = 0.0; :>> maximum = 11.0; :>> widthBits = 8; }
        attribute crc : Natural, CommandArgument { :>> minimum = 0.0; :>> maximum = 4294967295.0; :>> widthBits = 32; }
    }
    item pbuVerifyTable : CommandDefinition {
        doc /* Recompute and report a table checksum. */
        :>> opcodeLiteral = Opcode::PBU_VERIFY_TABLE; :>> opcodeNumber = 3076; :>> mnemonic = "PBU_VERIFY_TABLE";
        :>> application = ApplicationName::parameterBootUpdate; :>> apidClass = ApidClass::housekeeping; :>> apid = 971;
        :>> allowedModes = allFlightModes; :>> criticality = CommandCriticality::routine; :>> hazardous = false;
        :>> argumentCount = 1; :>> argumentBits = 8;
        attribute tableId : Natural, CommandArgument { :>> minimum = 0.0; :>> maximum = 11.0; :>> widthBits = 8; }
    }
    item pbuSetParameter : CommandDefinition {
        doc /* Set one parameter by id. */
        :>> opcodeLiteral = Opcode::PBU_SET_PARAMETER; :>> opcodeNumber = 3077; :>> mnemonic = "PBU_SET_PARAMETER";
        :>> application = ApplicationName::parameterBootUpdate; :>> apidClass = ApidClass::housekeeping; :>> apid = 971;
        :>> allowedModes = allFlightModes; :>> criticality = CommandCriticality::critical; :>> hazardous = false;
        :>> argumentCount = 2; :>> argumentBits = 48;
        attribute parameterId : Natural, CommandArgument { :>> minimum = 0.0; :>> maximum = 65535.0; :>> widthBits = 16; }
        attribute value : Real, CommandArgument { :>> minimum = -1000000000.0; :>> maximum = 1000000000.0; :>> widthBits = 32; }
    }
    item pbuGetParameter : CommandDefinition {
        doc /* Report one parameter by id. */
        :>> opcodeLiteral = Opcode::PBU_GET_PARAMETER; :>> opcodeNumber = 3078; :>> mnemonic = "PBU_GET_PARAMETER";
        :>> application = ApplicationName::parameterBootUpdate; :>> apidClass = ApidClass::housekeeping; :>> apid = 971;
        :>> allowedModes = allFlightModes; :>> criticality = CommandCriticality::routine; :>> hazardous = false;
        :>> argumentCount = 1; :>> argumentBits = 16;
        attribute parameterId : Natural, CommandArgument { :>> minimum = 0.0; :>> maximum = 65535.0; :>> widthBits = 16; }
    }
    item pbuStartBootUpdate : CommandDefinition {
        doc /* Start receiving a boot image. */
        :>> opcodeLiteral = Opcode::PBU_START_BOOT_UPDATE; :>> opcodeNumber = 3079; :>> mnemonic = "PBU_START_BOOT_UPDATE";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = true;
        :>> argumentCount = 2; :>> argumentBits = 40;
        attribute image : Natural, CommandArgument { :>> minimum = 0.0; :>> maximum = 1.0; :>> widthBits = 8; }
        attribute byteCount : Natural, CommandArgument { :>> minimum = 1.0; :>> maximum = 8388608.0; :>> widthBits = 32; }
    }
    item pbuAbortBootUpdate : CommandDefinition {
        doc /* Abort a boot image transfer. */
        :>> opcodeLiteral = Opcode::PBU_ABORT_BOOT_UPDATE; :>> opcodeNumber = 3080; :>> mnemonic = "PBU_ABORT_BOOT_UPDATE";
        :>> application = ApplicationName::parameterBootUpdate; :>> apidClass = ApidClass::housekeeping; :>> apid = 971;
        :>> allowedModes = allFlightModes; :>> criticality = CommandCriticality::critical; :>> hazardous = false;
        :>> argumentCount = 0; :>> argumentBits = 0;
    }
    item pbuSelectBootImage : CommandDefinition {
        doc /* Select the boot image used at the next reset. */
        :>> opcodeLiteral = Opcode::PBU_SELECT_BOOT_IMAGE; :>> opcodeNumber = 3081; :>> mnemonic = "PBU_SELECT_BOOT_IMAGE";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = true;
        :>> argumentCount = 2; :>> argumentBits = 24;
        attribute image : Natural, CommandArgument { :>> minimum = 0.0; :>> maximum = 1.0; :>> widthBits = 8; }
        attribute confirmKey : Natural, CommandArgument { :>> minimum = 0.0; :>> maximum = 65535.0; :>> widthBits = 16; }
    }
    item pbuCommitBootImage : CommandDefinition {
        doc /* Mark the running image good so the boot loader stops falling back. */
        :>> opcodeLiteral = Opcode::PBU_COMMIT_BOOT_IMAGE; :>> opcodeNumber = 3082; :>> mnemonic = "PBU_COMMIT_BOOT_IMAGE";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = true;
        :>> argumentCount = 0; :>> argumentBits = 0;
    }
    item pbuTableReset01 : CommandDefinition {
        doc /* Reset parameter table 1 to its flight defaults. */
        :>> opcodeLiteral = Opcode::PBU_TABLE_RESET_01; :>> opcodeNumber = 3083; :>> mnemonic = "PBU_TABLE_RESET_01";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset02 : CommandDefinition {
        doc /* Reset parameter table 2 to its flight defaults. */
        :>> opcodeLiteral = Opcode::PBU_TABLE_RESET_02; :>> opcodeNumber = 3084; :>> mnemonic = "PBU_TABLE_RESET_02";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset03 : CommandDefinition {
        doc /* Reset parameter table 3 to its flight defaults. */
        :>> opcodeLiteral = Opcode::PBU_TABLE_RESET_03; :>> opcodeNumber = 3085; :>> mnemonic = "PBU_TABLE_RESET_03";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset04 : CommandDefinition {
        doc /* Reset parameter table 4 to its flight defaults. */
        :>> opcodeLiteral = Opcode::PBU_TABLE_RESET_04; :>> opcodeNumber = 3086; :>> mnemonic = "PBU_TABLE_RESET_04";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset05 : CommandDefinition {
        doc /* Reset parameter table 5 to its flight defaults. */
        :>> opcodeLiteral = Opcode::PBU_TABLE_RESET_05; :>> opcodeNumber = 3087; :>> mnemonic = "PBU_TABLE_RESET_05";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset06 : CommandDefinition {
        doc /* Reset parameter table 6 to its flight defaults. */
        :>> opcodeLiteral = Opcode::PBU_TABLE_RESET_06; :>> opcodeNumber = 3088; :>> mnemonic = "PBU_TABLE_RESET_06";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset07 : CommandDefinition {
        doc /* Reset parameter table 7 to its flight defaults. */
        :>> opcodeLiteral = Opcode::PBU_TABLE_RESET_07; :>> opcodeNumber = 3089; :>> mnemonic = "PBU_TABLE_RESET_07";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset08 : CommandDefinition {
        doc /* Reset parameter table 8 to its flight defaults. */
        :>> opcodeLiteral = Opcode::PBU_TABLE_RESET_08; :>> opcodeNumber = 3090; :>> mnemonic = "PBU_TABLE_RESET_08";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset09 : CommandDefinition {
        doc /* Reset parameter table 9 to its flight defaults. */
        :>> opcodeLiteral = Opcode::PBU_TABLE_RESET_09; :>> opcodeNumber = 3091; :>> mnemonic = "PBU_TABLE_RESET_09";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset10 : CommandDefinition {
        doc /* Reset parameter table 10 to its flight defaults. */
        :>> opcodeLiteral = Opcode::PBU_TABLE_RESET_10; :>> opcodeNumber = 3092; :>> mnemonic = "PBU_TABLE_RESET_10";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset11 : CommandDefinition {
        doc /* Reset parameter table 11 to its flight defaults. */
        :>> opcodeLiteral = Opcode::PBU_TABLE_RESET_11; :>> opcodeNumber = 3093; :>> mnemonic = "PBU_TABLE_RESET_11";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }
    item pbuTableReset12 : CommandDefinition {
        doc /* Reset parameter table 12 to its flight defaults. */
        :>> opcodeLiteral = Opcode::PBU_TABLE_RESET_12; :>> opcodeNumber = 3094; :>> mnemonic = "PBU_TABLE_RESET_12";
        :>> application = ApplicationName::parameterBootUpdate; :>> apidClass = ApidClass::housekeeping; :>> apid = 971;
        :>> allowedModes = (TugMode::earlyOperations, TugMode::coast, TugMode::droHold, TugMode::safe); :>> criticality = CommandCriticality::critical; :>> hazardous = false;
        :>> argumentCount = 0; :>> argumentBits = 0;
    }

    // ---- telemetry dictionary: 961 points ------------------------------------------
    item cdhTBoard01 : TemperaturePoint {
        :>> mnemonic = "CDH_T_BOARD_01"; :>> pointId = 1001; :>> source = ApplicationName::cdh; :>> apidClass = ApidClass::housekeeping;
        :>> kind = TelemetryKind::housekeeping; :>> rate = 0.1 [Hz];
        :>> redLow = 233.0 [K]; :>> yellowLow = 253.0 [K]; :>> yellowHigh = 313.0 [K]; :>> redHigh = 333.0 [K];
    }
    item cdhTBoard02 : TemperaturePoint {
        :>> mnemonic = "CDH_T_BOARD_02"; :>> pointId = 1002; :>> source = ApplicationName::cdh; :>> apidClass = ApidClass::housekeeping;
        :>> kind = TelemetryKind::housekeeping; :>> rate = 0.1 [Hz];
        :>> redLow = 233.0 [K]; :>> yellowLow = 253.0 [K]; :>> yellowHigh = 313.0 [K]; :>> redHigh = 333.0 [K];
    }
    item cdhTBoard03 : TemperaturePoint {
        :>> mnemonic = "CDH_T_BOARD_03"; :>> pointId = 1003; :>> source = ApplicationName::cdh; :>> apidClass = ApidClass::housekeeping;
        :>> kind = TelemetryKind::housekeeping; :>> rate = 0.1 [Hz];
        :>> redLow = 233.0 [K]; :>> yellowLow = 253.0 [K]; :>> yellowHigh = 313.0 [K]; :>> redHigh = 333.0 [K];
    }
    item cdhTBoard04 : TemperaturePoint {
        :>> mnemonic = "CDH_T_BOARD_04"; :>> pointId = 1004; :>> source = ApplicationName::cdh; :>> apidClass = ApidClass::housekeeping;
        :>> kind = TelemetryKind::housekeeping; :>> rate = 0.1 [Hz];
        :>> redLow = 233.0 [K]; :>> yellowLow = 253.0 [K]; :>> yellowHigh = 313.0 [K]; :>> redHigh = 333.0 [K];
    }
    item cdhCpuLoad01 : FractionPoint {
        :>> mnemonic = "CDH_CPU_LOAD_01"; :>> pointId = 1005; :>> source = ApplicationName::cdh; :>> apidClass = ApidClass::housekeeping;
        :>> kind = TelemetryKind::housekeeping; :>> rate = 1.0 [Hz];
        :>> redLow = 0.0; :>> yellowLow = 0.1; :>> yellowHigh = 0.9; :>> redHigh = 1.0;
    }
    item cdhCpuLoad02 : FractionPoint {
        :>> mnemonic = "CDH_CPU_LOAD_02"; :>> pointId = 1006; :>> source = ApplicationName::cdh; :>> apidClass = ApidClass::housekeeping;
        :>> kind = TelemetryKind::housekeeping; :>> rate = 1.0 [Hz];
        :>> redLow = 0.0; :>> yellowLow = 0.1; :>> yellowHigh = 0.9; :>> redHigh = 1.0;
    }
    item cdhMemUsed01 : FractionPoint {
        :>> mnemonic = "CDH_MEM_USED_01"; :>> pointId = 1007; :>> source = ApplicationName::cdh; :>> apidClass = ApidClass::housekeeping;
        :>> kind = TelemetryKind::housekeeping; :>> rate = 1.0 [Hz];
        :>> redLow = 0.0; :>> yellowLow = 0.1; :>> yellowHigh = 0.9; :>> redHigh = 1.0;
    }
    item cdhMemUsed02 : FractionPoint {
        :>> mnemonic = "CDH_MEM_USED_02"; :>> pointId = 1008; :>> source = ApplicationName::cdh; :>> apidClass = ApidClass::housekeeping;
        :>> kind = TelemetryKind::housekeeping; :>> rate = 1.0 [Hz];
        :>> redLow = 0.0; :>> yellowLow = 0.1; :>> yellowHigh = 0.9; :>> redHigh = 1.0;
    }
    item cdhRecorderFill : FractionPoint {
        :>> mnemonic = "CDH_RECORDER_FILL"; :>> pointId = 1009; :>> source = ApplicationName::cdh; :>> apidClass = ApidClass::housekeeping;
        :>> kind = TelemetryKind::housekeeping; :>> rate = 0.1 [Hz];
        :>> redLow = 0.0; :>> yellowLow = 0.1; :>> yellowHigh = 0.9; :>> redHigh = 1.0;
    }
    item cdhUptime : DurationPoint {
        :>> mnemonic = "CDH_UPTIME"; :>> pointId = 1010; :>> source = ApplicationName::cdh; :>> apidClass = ApidClass::housekeeping;
        :>> kind = TelemetryKind::housekeeping; :>> rate = 1.0 [Hz];
        :>> redLow = 0.0 [s]; :>> yellowLow = 0.0 [s]; :>> yellowHigh = 10000000.0 [s]; :>> redHigh = 100000000.0 [s];
    }
    item cdhCmdAcceptCount : CountPoint {
        :>> mnemonic = "CDH_CMD_ACCEPT_COUNT"; :>> pointId = 1011; :>> source = ApplicationName::cdh; :>> apidClass = ApidClass::housekeeping;
        :>> kind = TelemetryKind::housekeeping; :>> rate = 1.0 [Hz];
        :>> redLow = 0; :>> yellowLow = 0; :>> yellowHigh = 61035 * 65536 + 10240; :>> redHigh = 65535 * 65536 + 65535;
    }
    item cdhCmdRejectCount : CountPoint {
        :>> mnemonic = "CDH_CMD_REJECT_COUNT"; :>> pointId = 1012; :>> source = ApplicationName::cdh; :>> apidClass = ApidClass::housekeeping;
        :>> kind = TelemetryKind::housekeeping; :>> rate = 1.0 [Hz];
        :>> redLow = 0; :>> yellowLow = 0; :>> yellowHigh = 10; :>> redHigh = 100;
    }
    item cdhBusMsgRate : CountPoint {
        :>> mnemonic = "CDH_BUS_MSG_RATE"; :>> pointId = 1013; :>> source = ApplicationName::cdh; :>> apidClass = ApidClass::housekeeping;
        :>> kind = TelemetryKind::engineering; :>> rate = 1.0 [Hz];
        :>> redLow = 0; :>> yellowLow = 0; :>> yellowHigh = 61035 * 65536 + 10240; :>> redHigh = 65535 * 65536 + 65535;
    }
    item cdhFileCount : CountPoint {
        :>> mnemonic = "CDH_FILE_COUNT"; :>> pointId = 1014; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhClockCoarse : CountPoint {
        :>> mnemonic = "CDH_CLOCK_COARSE"; :>> pointId = 1015; :>> source = ApplicationName::cdh; :>> apidClass = ApidClass::housekeeping;
        :>> kind = TelemetryKind::housekeeping; :>> rate = 1.0 [Hz];
        :>> redLow = 0; :>> yellowLow = 0; :>> yellowHigh = 61035 * 65536 + 10240; :>> redHigh = 65535 * 65536 + 65535;
    }
    item cdhClockFine : CountPoint {
        :>> mnemonic = "CDH_CLOCK_FINE"; :>> pointId = 1016; :>> source = ApplicationName::cdh; :>> apidClass = ApidClass::housekeeping;
        :>> kind = TelemetryKind::housekeeping; :>> rate = 1.0 [Hz];
        :>> redLow = 0; :>> yellowLow = 0; :>> yellowHigh = 61035 * 65536 + 10240; :>> redHigh = 65535 * 65536 + 65535;
    }
    item cdhAppRate01 : CountPoint {
        :>> mnemonic = "CDH_APP_RATE_01"; :>> pointId = 1017; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate02 : CountPoint {
        :>> mnemonic = "CDH_APP_RATE_02"; :>> pointId = 1018; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate03 : CountPoint {
        :>> mnemonic = "CDH_APP_RATE_03"; :>> pointId = 1019; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate04 : CountPoint {
        :>> mnemonic = "CDH_APP_RATE_04"; :>> pointId = 1020; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate05 : CountPoint {
        :>> mnemonic = "CDH_APP_RATE_05"; :>> pointId = 1021; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate06 : CountPoint {
        :>> mnemonic = "CDH_APP_RATE_06"; :>> pointId = 1022; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate07 : CountPoint {
        :>> mnemonic = "CDH_APP_RATE_07"; :>> pointId = 1023; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate08 : CountPoint {
        :>> mnemonic = "CDH_APP_RATE_08"; :>> pointId = 1024; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate09 : CountPoint {
        :>> mnemonic = "CDH_APP_RATE_09"; :>> pointId = 1025; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate10 : CountPoint {
        :>> mnemonic = "CDH_APP_RATE_10"; :>> pointId = 1026; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate11 : CountPoint {
        :>> mnemonic = "CDH_APP_RATE_11"; :>> pointId = 1027; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppRate12 : CountPoint {
        :>> mnemonic = "CDH_APP_RATE_12"; :>> pointId = 1028; :>> source = ApplicationName::cdh; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item cdhAppLoad01 : FractionPoint {
        :>> mnemonic = "CDH_APP_LOAD_01"; :>> pointId = 1029; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad02 : FractionPoint {
        :>> mnemonic = "CDH_APP_LOAD_02"; :>> pointId = 1030; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad03 : FractionPoint {
        :>> mnemonic = "CDH_APP_LOAD_03"; :>> pointId = 1031; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad04 : FractionPoint {
        :>> mnemonic = "CDH_APP_LOAD_04"; :>> pointId = 1032; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad05 : FractionPoint {
        :>> mnemonic = "CDH_APP_LOAD_05"; :>> pointId = 1033; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad06 : FractionPoint {
        :>> mnemonic = "CDH_APP_LOAD_06"; :>> pointId = 1034; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad07 : FractionPoint {
        :>> mnemonic = "CDH_APP_LOAD_07"; :>> pointId = 1035; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad08 : FractionPoint {
        :>> mnemonic = "CDH_APP_LOAD_08"; :>> pointId = 1036; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad09 : FractionPoint {
        :>> mnemonic = "CDH_APP_LOAD_09"; :>> pointId = 1037; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad10 : FractionPoint {
        :>> mnemonic = "CDH_APP_LOAD_10"; :>> pointId = 1038; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad11 : FractionPoint {
        :>> mnemonic = "CDH_APP_LOAD_11"; :>> pointId = 1039; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhAppLoad12 : FractionPoint {
        :>> mnemonic = "CDH_APP_LOAD_12"; :>> pointId = 1040; :>> source = ApplicationName::cdh; :>> apidClass = ApidClass::housekeeping;
        :>> kind = TelemetryKind::engineering; :>> rate = 0.1 [Hz];
        :>> redLow = 0.0; :>> yellowLow = 0.1; :>> yellowHigh = 0.9; :>> redHigh = 1.0;
    }
    item cdhPartitionStatus01 : StatusPoint {
        :>> mnemonic = "CDH_PARTITION_STATUS_01"; :>> pointId = 1041; :>> source = ApplicationName::cdh; :>> apidClass = ApidClass::housekeeping;
        :>> kind = TelemetryKind::housekeeping; :>> rate = 1.0 [Hz];
        :>> redLow = 0; :>> yellowLow = 0; :>> yellowHigh = 254; :>> redHigh = 255;
    }
    item cdhPartitionStatus02 : StatusPoint {
        :>> mnemonic = "CDH_PARTITION_STATUS_02"; :>> pointId = 1042; :>> source = ApplicationName::cdh; :>> apidClass = ApidClass::housekeeping;
        :>> kind = TelemetryKind::housekeeping; :>> rate = 1.0 [Hz];
        :>> redLow = 0; :>> yellowLow = 0; :>> yellowHigh = 254; :>> redHigh = 255;
    }
    item cdhPartitionStatus03 : StatusPoint {
        :>> mnemonic = "CDH_PARTITION_STATUS_03"; :>> pointId = 1043; :>> source = ApplicationName::cdh; :>> apidClass = ApidClass::housekeeping;
        :>> kind = TelemetryKind::housekeeping; :>> rate = 1.0 [Hz];
        :>> redLow = 0; :>> yellowLow = 0; :>> yellowHigh = 254; :>> redHigh = 255;
    }
    item cdhPartitionStatus04 : StatusPoint {
        :>> mnemonic = "CDH_PARTITION_STATUS_04"; :>> pointId = 1044; :>> source = ApplicationName::cdh; :>> apidClass = ApidClass::housekeeping;
        :>> kind = TelemetryKind::housekeeping; :>> rate = 1.0 [Hz];
        :>> redLow = 0; :>> yellowLow = 0; :>> yellowHigh = 254; :>> redHigh = 255;
    }
    item cdhBusRtErrors01 : CountPoint {
        :>> mnemonic = "CDH_BUS_RT_ERRORS_01"; :>> pointId = 1045; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors02 : CountPoint {
        :>> mnemonic = "CDH_BUS_RT_ERRORS_02"; :>> pointId = 1046; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors03 : CountPoint {
        :>> mnemonic = "CDH_BUS_RT_ERRORS_03"; :>> pointId = 1047; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors04 : CountPoint {
        :>> mnemonic = "CDH_BUS_RT_ERRORS_04"; :>> pointId = 1048; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors05 : CountPoint {
        :>> mnemonic = "CDH_BUS_RT_ERRORS_05"; :>> pointId = 1049; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors06 : CountPoint {
        :>> mnemonic = "CDH_BUS_RT_ERRORS_06"; :>> pointId = 1050; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors07 : CountPoint {
        :>> mnemonic = "CDH_BUS_RT_ERRORS_07"; :>> pointId = 1051; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors08 : CountPoint {
        :>> mnemonic = "CDH_BUS_RT_ERRORS_08"; :>> pointId = 1052; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors09 : CountPoint {
        :>> mnemonic = "CDH_BUS_RT_ERRORS_09"; :>> pointId = 1053; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors10 : CountPoint {
        :>> mnemonic = "CDH_BUS_RT_ERRORS_10"; :>> pointId = 1054; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors11 : CountPoint {
        :>> mnemonic = "CDH_BUS_RT_ERRORS_11"; :>> pointId = 1055; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors12 : CountPoint {
        :>> mnemonic = "CDH_BUS_RT_ERRORS_12"; :>> pointId = 1056; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors13 : CountPoint {
        :>> mnemonic = "CDH_BUS_RT_ERRORS_13"; :>> pointId = 1057; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors14 : CountPoint {
        :>> mnemonic = "CDH_BUS_RT_ERRORS_14"; :>> pointId = 1058; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors15 : CountPoint {
        :>> mnemonic = "CDH_BUS_RT_ERRORS_15"; :>> pointId = 1059; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhBusRtErrors16 : CountPoint {
        :>> mnemonic = "CDH_BUS_RT_ERRORS_16"; :>> pointId = 1060; :>> source = ApplicationName::cdh; :>> apidClass = ApidClass::housekeeping;
        :>> kind = TelemetryKind::engineering; :>> rate = 0.1 [Hz];
        :>> redLow = 0; :>> yellowLow = 0; :>> yellowHigh = 10; :>> redHigh = 100;
    }
    item cdhWatchdogMargin : DurationPoint {
        :>> mnemonic = "CDH_WATCHDOG_MARGIN"; :>> pointId = 1061; :>> source = ApplicationName::cdh; :>> apidClass = ApidClass::housekeeping;
        :>> kind = TelemetryKind::housekeeping; :>> rate = 1.0 [Hz];
        :>> redLow = 0.0 [s]; :>> yellowLow = 0.5 [s]; :>> yellowHigh = 30.0 [s]; :>> redHigh = 60.0 [s];
    }
    item gncQ01 : FractionPoint {
        :>> mnemonic = "GNC_Q_01"; :>> pointId = 2001; :>> source = ApplicationName::gnc; :>> apidClass = ApidClass::guidance;
        :>> kind = TelemetryKind::housekeeping; :>> rate = 1.0 [Hz];
        :>> redLow = -1.0; :>> yellowLow = -1.0; :>> yellowHigh = 1.0; :>> redHigh = 1.0;
    }
    item gncQ02 : FractionPoint {
        :>> mnemonic = "GNC_Q_02"; :>> pointId = 2002; :>> source = ApplicationName::gnc; :>> apidClass = ApidClass::guidance;
        :>> kind = TelemetryKind::housekeeping; :>> rate = 1.0 [Hz];
        :>> redLow = -1.0; :>> yellowLow = -1.0; :>> yellowHigh = 1.0; :>> redHigh = 1.0;
    }
    item gncQ03 : FractionPoint {
        :>> mnemonic = "GNC_Q_03"; :>> pointId = 2003; :>> source = ApplicationName::gnc; :>> apidClass = ApidClass::guidance;
        :>> kind = TelemetryKind::housekeeping; :>> rate = 1.0 [Hz];
        :>> redLow = -1.0; :>> yellowLow = -1.0; :>> yellowHigh = 1.0; :>> redHigh = 1.0;
    }
    item gncQ04 : FractionPoint {
        :>> mnemonic = "GNC_Q_04"; :>> pointId = 2004; :>> source = ApplicationName::gnc; :>> apidClass = ApidClass::guidance;
        :>> kind = TelemetryKind::housekeeping; :>> rate = 1.0 [Hz];
        :>> redLow = -1.0; :>> yellowLow = -1.0; :>> yellowHigh = 1.0; :>> redHigh = 1.0;
    }
    item gncRate01 : AngularRatePoint {
        :>> mnemonic = "GNC_RATE_01"; :>> pointId = 2005; :>> source = ApplicationName::gnc; :>> apidClass = ApidClass::guidance;
        :>> kind = TelemetryKind::housekeeping; :>> rate = 1.0 [Hz];
        :>> redLow = -0.1 [rad/s]; :>> yellowLow = -0.05 [rad/s]; :>> yellowHigh = 0.05 [rad/s]; :>> redHigh = 0.1 [rad/s];
    }
    item gncRate02 : AngularRatePoint {
        :>> mnemonic = "GNC_RATE_02"; :>> pointId = 2006; :>> source = ApplicationName::gnc; :>> apidClass = ApidClass::guidance;
        :>> kind = TelemetryKind::housekeeping; :>> rate = 1.0 [Hz];
        :>> redLow = -0.1 [rad/s]; :>> yellowLow = -0.05 [rad/s]; :>> yellowHigh = 0.05 [rad/s]; :>> redHigh = 0.1 [rad/s];
    }
    item gncRate03 : AngularRatePoint {
        :>> mnemonic = "GNC_RATE_03"; :>> pointId = 2007; :>> source = ApplicationName::gnc; :>> apidClass = ApidClass::guidance;
        :>> kind = TelemetryKind::housekeeping; :>> rate = 1.0 [Hz];
        :>> redLow = -0.1 [rad/s]; :>> yellowLow = -0.05 [rad/s]; :>> yellowHigh = 0.05 [rad/s]; :>> redHigh = 0.1 [rad/s];
    }
    item gncAttErr01 : AnglePoint {
        :>> mnemonic = "GNC_ATT_ERR_01"; :>> pointId = 2008; :>> source = ApplicationName::gnc; :>> apidClass = ApidClass::guidance;
        :>> kind = TelemetryKind::housekeeping; :>> rate = 1.0 [Hz];
        :>> redLow = -0.1 [rad]; :>> yellowLow = -0.02 [rad]; :>> yellowHigh = 0.02 [rad]; :>> redHigh = 0.1 [rad];
    }
    item gncAttErr02 : AnglePoint {
        :>> mnemonic = "GNC_ATT_ERR_02"; :>> pointId = 2009; :>> source = ApplicationName::gnc; :>> apidClass = ApidClass::guidance;
        :>> kind = TelemetryKind::housekeeping; :>> rate = 1.0 [Hz];
        :>> redLow = -0.1 [rad]; :>> yellowLow = -0.02 [rad]; :>> yellowHigh = 0.02 [rad]; :>> redHigh = 0.1 [rad];
    }
    item gncAttErr03 : AnglePoint {
        :>> mnemonic = "GNC_ATT_ERR_03"; :>> pointId = 2010; :>> source = ApplicationName::gnc; :>> apidClass = ApidClass::guidance;
        :>> kind = TelemetryKind::housekeeping; :>> rate = 1.0 [Hz];
        :>> redLow = -0.1 [rad]; :>> yellowLow = -0.02 [rad]; :>> yellowHigh = 0.02 [rad]; :>> redHigh = 0.1 [rad];
    }
    item gncRateErr01 : AngularRatePoint {
        :>> mnemonic = "GNC_RATE_ERR_01"; :>> pointId = 2011; :>> source = ApplicationName::gnc; :>> apidClass = ApidClass::guidance;
        :>> kind = TelemetryKind::engineering; :>> rate = 1.0 [Hz];
        :>> redLow = -0.1 [rad/s]; :>> yellowLow = -0.05 [rad/s]; :>> yellowHigh = 0.05 [rad/s]; :>> redHigh = 0.1 [rad/s];
    }
    item gncRateErr02 : AngularRatePoint {
        :>> mnemonic = "GNC_RATE_ERR_02"; :>> pointId = 2012; :>> source = ApplicationName::gnc; :>> apidClass = ApidClass::guidance;
        :>> kind = TelemetryKind::engineering; :>> rate = 1.0 [Hz];
        :>> redLow = -0.1 [rad/s]; :>> yellowLow = -0.05 [rad/s]; :>> yellowHigh = 0.05 [rad/s]; :>> redHigh = 0.1 [rad/s];
    }
    item gncRateErr03 : AngularRatePoint {
        :>> mnemonic = "GNC_RATE_ERR_03"; :>> pointId = 2013; :>> source = ApplicationName::gnc; :>> apidClass = ApidClass::guidance;
        :>> kind = TelemetryKind::engineering; :>> rate = 1.0 [Hz];
        :>> redLow = -0.1 [rad/s]; :>> yellowLow = -0.05 [rad/s]; :>> yellowHigh = 0.05 [rad/s]; :>> redHigh = 0.1 [rad/s];
    }
    item gncStT01 : TemperaturePoint {
        :>> mnemonic = "GNC_ST_T_01"; :>> pointId = 2014; :>> source = ApplicationName::gnc; :>> apidClass = ApidClass::guidance;
        :>> kind = TelemetryKind::engineering; :>> rate = 0.1 [Hz];
        :>> redLow = 233.0 [K]; :>> yellowLow = 253.0 [K]; :>> yellowHigh = 313.0 [K]; :>> redHigh = 333.0 [K];
    }
    item gncStT02 : TemperaturePoint {
        :>> mnemonic = "GNC_ST_T_02"; :>> pointId = 2015; :>> source = ApplicationName::gnc; :>> apidClass = ApidClass::guidance;
        :>> kind = TelemetryKind::engineering; :>> rate = 0.1 [Hz];
        :>> redLow = 233.0 [K]; :>> yellowLow = 253.0 [K]; :>> yellowHigh = 313.0 [K]; :>> redHigh = 333.0 [K];
    }
    item gncStStatus01 : StatusPoint {
        :>> mnemonic = "GNC_ST_STATUS_01"; :>> pointId = 2016; :>> source = ApplicationName::gnc; :>> apidClass = ApidClass::guidance;
        :>> kind = TelemetryKind::housekeeping; :>> rate = 1.0 [Hz];
        :>> redLow = 0; :>> yellowLow = 0; :>> yellowHigh = 254; :>> redHigh = 255;
    }
    item gncStStatus02 : StatusPoint {
        :>> mnemonic = "GNC_ST_STATUS_02"; :>> pointId = 2017; :>> source = ApplicationName::gnc; :>> apidClass = ApidClass::guidance;
        :>> kind = TelemetryKind::housekeeping; :>> rate = 1.0 [Hz];
        :>> redLow = 0; :>> yellowLow = 0; :>> yellowHigh = 254; :>> redHigh = 255;
    }
    item gncImuGyro01 : AngularRatePoint {
        :>> mnemonic = "GNC_IMU_GYRO_01"; :>> pointId = 2018; :>> source = ApplicationName::gnc; :>> apidClass = ApidClass::guidance;
        :>> kind = TelemetryKind::engineering; :>> rate = 10.0 [Hz];
        :>> redLow = -0.1 [rad/s]; :>> yellowLow = -0.05 [rad/s]; :>> yellowHigh = 0.05 [rad/s]; :>> redHigh = 0.1 [rad/s];
    }
    item gncImuGyro02 : AngularRatePoint {
        :>> mnemonic = "GNC_IMU_GYRO_02"; :>> pointId = 2019; :>> source = ApplicationName::gnc; :>> apidClass = ApidClass::guidance;
        :>> kind = TelemetryKind::engineering; :>> rate = 10.0 [Hz];
        :>> redLow = -0.1 [rad/s]; :>> yellowLow = -0.05 [rad/s]; :>> yellowHigh = 0.05 [rad/s]; :>> redHigh = 0.1 [rad/s];
    }
    item gncImuGyro03 : AngularRatePoint {
        :>> mnemonic = "GNC_IMU_GYRO_03"; :>> pointId = 2020; :>> source = ApplicationName::gnc; :>> apidClass = ApidClass::guidance;
        :>> kind = TelemetryKind::engineering; :>> rate = 10.0 [Hz];
        :>> redLow = -0.1 [rad/s]; :>> yellowLow = -0.05 [rad/s]; :>> yellowHigh = 0.05 [rad/s]; :>> redHigh = 0.1 [rad/s];
    }
    item gncImuGyro04 : AngularRatePoint {
        :>> mnemonic = "GNC_IMU_GYRO_04"; :>> pointId = 2021; :>> source = ApplicationName::gnc; :>> apidClass = ApidClass::guidance;
        :>> kind = TelemetryKind::engineering; :>> rate = 10.0 [Hz];
        :>> redLow = -0.1 [rad/s]; :>> yellowLow = -0.05 [rad/s]; :>> yellowHigh = 0.05 [rad/s]; :>> redHigh = 0.1 [rad/s];
    }
    item gncImuGyro05 : AngularRatePoint {
        :>> mnemonic = "GNC_IMU_GYRO_05"; :>> pointId = 2022; :>> source = ApplicationName::gnc; :>> apidClass = ApidClass::guidance;
        :>> kind = TelemetryKind::engineering; :>> rate = 10.0 [Hz];
        :>> redLow = -0.1 [rad/s]; :>> yellowLow = -0.05 [rad/s]; :>> yellowHigh = 0.05 [rad/s]; :>> redHigh = 0.1 [rad/s];
    }
    item gncImuGyro06 : AngularRatePoint {
        :>> mnemonic = "GNC_IMU_GYRO_06"; :>> pointId = 2023; :>> source = ApplicationName::gnc; :>> apidClass = ApidClass::guidance;
        :>> kind = TelemetryKind::engineering; :>> rate = 10.0 [Hz];
        :>> redLow = -0.1 [rad/s]; :>> yellowLow = -0.05 [rad/s]; :>> yellowHigh = 0.05 [rad/s]; :>> redHigh = 0.1 [rad/s];
    }
    item gncImuAccel01 : SpeedPoint {
        :>> mnemonic = "GNC_IMU_ACCEL_01"; :>> pointId = 2024; :>> source = ApplicationName::gnc; :>> apidClass = ApidClass::guidance;
        :>> kind = TelemetryKind::engineering; :>> rate = 10.0 [Hz];
        :>> redLow = -10.0 [m/s]; :>> yellowLow = -5.0 [m/s]; :>> yellowHigh = 5.0 [m/s]; :>> redHigh = 10.0 [m/s];
    }
    item gncImuAccel02 : SpeedPoint {
        :>> mnemonic = "GNC_IMU_ACCEL_02"; :>> pointId = 2025; :>> source = ApplicationName::gnc; :>> apidClass = ApidClass::guidance;
        :>> kind = TelemetryKind::engineering; :>> rate = 10.0 [Hz];
        :>> redLow = -10.0 [m/s]; :>> yellowLow = -5.0 [m/s]; :>> yellowHigh = 5.0 [m/s]; :>> redHigh = 10.0 [m/s];
    }
    item gncImuAccel03 : SpeedPoint {
        :>> mnemonic = "GNC_IMU_ACCEL_03"; :>> pointId = 2026; :>> source = ApplicationName::gnc; :>> apidClass = ApidClass::guidance;
        :>> kind = TelemetryKind::engineering; :>> rate = 10.0 [Hz];
        :>> redLow = -10.0 [m/s]; :>> yellowLow = -5.0 [m/s]; :>> yellowHigh = 5.0 [m/s]; :>> redHigh = 10.0 [m/s];
    }
    item gncImuAccel04 : SpeedPoint {
        :>> mnemonic = "GNC_IMU_ACCEL_04"; :>> pointId = 2027; :>> source = ApplicationName::gnc; :>> apidClass = ApidClass::guidance;
        :>> kind = TelemetryKind::engineering; :>> rate = 10.0 [Hz];
        :>> redLow = -10.0 [m/s]; :>> yellowLow = -5.0 [m/s]; :>> yellowHigh = 5.0 [m/s]; :>> redHigh = 10.0 [m/s];
    }
    item gncImuAccel05 : SpeedPoint {
        :>> mnemonic = "GNC_IMU_ACCEL_05"; :>> pointId = 2028; :>> source = ApplicationName::gnc; :>> apidClass = ApidClass::guidance;
        :>> kind = TelemetryKind::engineering; :>> rate = 10.0 [Hz];
        :>> redLow = -10.0 [m/s]; :>> yellowLow = -5.0 [m/s]; :>> yellowHigh = 5.0 [m/s]; :>> redHigh = 10.0 [m/s];
    }
    item gncImuAccel06 : SpeedPoint {
        :>> mnemonic = "GNC_IMU_ACCEL_06"; :>> pointId = 2029; :>> source = ApplicationName::gnc; :>> apidClass = ApidClass::guidance;
        :>> kind = TelemetryKind::engineering; :>> rate = 10.0 [Hz];
        :>> redLow = -10.0 [m/s]; :>> yellowLow = -5.0 [m/s]; :>> yellowHigh = 5.0 [m/s]; :>> redHigh = 10.0 [m/s];
    }
    item gncImuT01 : TemperaturePoint {
        :>> mnemonic = "GNC_IMU_T_01"; :>> pointId = 2030; :>> source = ApplicationName::gnc; :>> apidClass = ApidClass::guidance;
        :>> kind = TelemetryKind::engineering; :>> rate = 0.1 [Hz];
        :>> redLow = 233.0 [K]; :>> yellowLow = 253.0 [K]; :>> yellowHigh = 313.0 [K]; :>> redHigh = 333.0 [K];
    }
    item gncImuT02 : TemperaturePoint {
        :>> mnemonic = "GNC_IMU_T_02"; :>> pointId = 2031; :>> source = ApplicationName::gnc; :>> apidClass = ApidClass::guidance;
        :>> kind = TelemetryKind::engineering; :>> rate = 0.1 [Hz];
        :>> redLow = 233.0 [K]; :>> yellowLow = 253.0 [K]; :>> yellowHigh = 313.0 [K]; :>> redHigh = 333.0 [K];
    }
    item gncWheelSpeed01 : AngularRatePoint {
        :>> mnemonic = "GNC_WHEEL_SPEED_01"; :>> pointId = 2032; :>> source = ApplicationName::gnc; :>> apidClass = ApidClass::guidance;
        :>> kind = TelemetryKind::housekeeping; :>> rate = 1.0 [Hz];
        :>> redLow = -650.0 [rad/s]; :>> yellowLow = -600.0 [rad/s]; :>> yellowHigh = 600.0 [rad/s]; :>> redHigh = 650.0 [rad/s];
    }
    item gncWheelSpeed02 : AngularRatePoint {
        :>> mnemonic = "GNC_WHEEL_SPEED_02"; :>> pointId = 2033; :>> source = ApplicationName::gnc; :>> apidClass = ApidClass::guidance;
        :>> kind = TelemetryKind::housekeeping; :>> rate = 1.0 [Hz];
        :>> redLow = -650.0 [rad/s]; :>> yellowLow = -600.0 [rad/s]; :>> yellowHigh = 600.0 [rad/s]; :>> redHigh = 650.0 [rad/s];
    }
    item gncWheelSpeed03 : AngularRatePoint {
        :>> mnemonic = "GNC_WHEEL_SPEED_03"; :>> pointId = 2034; :>> source = ApplicationName::gnc; :>> apidClass = ApidClass::guidance;
        :>> kind = TelemetryKind::housekeeping; :>> rate = 1.0 [Hz];
        :>> redLow = -650.0 [rad/s]; :>> yellowLow = -600.0 [rad/s]; :>> yellowHigh = 600.0 [rad/s]; :>> redHigh = 650.0 [rad/s];
    }
    item gncWheelSpeed04 : AngularRatePoint {
        :>> mnemonic = "GNC_WHEEL_SPEED_04"; :>> pointId = 2035; :>> source = ApplicationName::gnc; :>> apidClass = ApidClass::guidance;
        :>> kind = TelemetryKind::housekeeping; :>> rate = 1.0 [Hz];
        :>> redLow = -650.0 [rad/s]; :>> yellowLow = -600.0 [rad/s]; :>> yellowHigh = 600.0 [rad/s]; :>> redHigh = 650.0 [rad/s];
    }
    item gncWheelI01 : CurrentPoint {
        :>> mnemonic = "GNC_WHEEL_I_01"; :>> pointId = 2036; :>> source = ApplicationName::gnc; :>> apidClass = ApidClass::guidance;
        :>> kind = TelemetryKind::engineering; :>> rate = 1.0 [Hz];
        :>> redLow = 0.0 [A]; :>> yellowLow = 0.0 [A]; :>> yellowHigh = 8.0 [A]; :>> redHigh = 10.0 [A];
    }
    item gncWheelI02 : CurrentPoint {
        :>> mnemonic = "GNC_WHEEL_I_02"; :>> pointId = 2037; :>> source = ApplicationName::gnc; :>> apidClass = ApidClass::guidance;
        :>> kind = TelemetryKind::engineering; :>> rate = 1.0 [Hz];
        :>> redLow = 0.0 [A]; :>> yellowLow = 0.0 [A]; :>> yellowHigh = 8.0 [A]; :>> redHigh = 10.0 [A];
    }
    item gncWheelI03 : CurrentPoint {
        :>> mnemonic = "GNC_WHEEL_I_03"; :>> pointId = 2038; :>> source = ApplicationName::gnc; :>> apidClass = ApidClass::guidance;
        :>> kind = TelemetryKind::engineering; :>> rate = 1.0 [Hz];
        :>> redLow = 0.0 [A]; :>> yellowLow = 0.0 [A]; :>> yellowHigh = 8.0 [A]; :>> redHigh = 10.0 [A];
    }
    item gncWheelI04 : CurrentPoint {
        :>> mnemonic = "GNC_WHEEL_I_04"; :>> pointId = 2039; :>> source = ApplicationName::gnc; :>> apidClass = ApidClass::guidance;
        :>> kind = TelemetryKind::engineering; :>> rate = 1.0 [Hz];
        :>> redLow = 0.0 [A]; :>> yellowLow = 0.0 [A]; :>> yellowHigh = 8.0 [A]; :>> redHigh = 10.0 [A];
    }
    item gncWheelT01 : TemperaturePoint {
        :>> mnemonic = "GNC_WHEEL_T_01"; :>> pointId = 2040; :>> source = ApplicationName::gnc; :>> apidClass = ApidClass::guidance;
        :>> kind = TelemetryKind::engineering; :>> rate = 0.1 [Hz];
        :>> redLow = 233.0 [K]; :>> yellowLow = 253.0 [K]; :>> yellowHigh = 313.0 [K]; :>> redHigh = 333.0 [K];
    }
    item gncWheelT02 : TemperaturePoint {
        :>> mnemonic = "GNC_WHEEL_T_02"; :>> pointId = 2041; :>> source = ApplicationName::gnc; :>> apidClass = ApidClass::guidance;
        :>> kind = TelemetryKind::engineering; :>> rate = 0.1 [Hz];
        :>> redLow = 233.0 [K]; :>> yellowLow = 253.0 [K]; :>> yellowHigh = 313.0 [K]; :>> redHigh = 333.0 [K];
    }
    item gncWheelT03 : TemperaturePoint {
        :>> mnemonic = "GNC_WHEEL_T_03"; :>> pointId = 2042; :>> source = ApplicationName::gnc; :>> apidClass = ApidClass::guidance;
        :>> kind = TelemetryKind::engineering; :>> rate = 0.1 [Hz];
        :>> redLow = 233.0 [K]; :>> yellowLow = 253.0 [K]; :>> yellowHigh = 313.0 [K]; :>> redHigh = 333.0 [K];
    }
    item gncWheelT04 : TemperaturePoint {
        :>> mnemonic = "GNC_WHEEL_T_04"; :>> pointId = 2043; :>> source = ApplicationName::gnc; :>> apidClass = ApidClass::guidance;
        :>> kind = TelemetryKind::engineering; :>> rate = 0.1 [Hz];
        :>> redLow = 233.0 [K]; :>> yellowLow = 253.0 [K]; :>> yellowHigh = 313.0 [K]; :>> redHigh = 333.0 [K];
    }
    item gncRcsOnTime01 : DurationPoint {
        :>> mnemonic = "GNC_RCS_ON_TIME_01"; :>> pointId = 2044; :>> source = ApplicationName::gnc; :>> apidClass = ApidClass::guidance;
        :>> kind = TelemetryKind::engineering; :>> rate = 0.1 [Hz];
        :>> redLow = 0.0 [s]; :>> yellowLow = 0.0 [s]; :>> yellowHigh = 10000000.0 [s]; :>> redHigh = 100000000.0 [s];
    }
    item gncRcsOnTime02 : DurationPoint {
        :>> mnemonic = "GNC_RCS_ON_TIME_02"; :>> pointId = 2045; :>> source = ApplicationName::gnc; :>> apidClass = ApidClass::guidance;
        :>> kind = TelemetryKind::engineering; :>> rate = 0.1 [Hz];
        :>> redLow = 0.0 [s]; :>> yellowLow = 0.0 [s]; :>> yellowHigh = 10000000.0 [s]; :>> redHigh = 100000000.0 [s];
    }
    item gncRcsOnTime03 : DurationPoint {
        :>> mnemonic = "GNC_RCS_ON_TIME_03"; :>> pointId = 2046; :>> source = ApplicationName::gnc; :>> apidClass = ApidClass::guidance;
        :>> kind = TelemetryKind::engineering; :>> rate = 0.1 [Hz];
        :>> redLow = 0.0 [s]; :>> yellowLow = 0.0 [s]; :>> yellowHigh = 10000000.0 [s]; :>> redHigh = 100000000.0 [s];
    }
    item gncRcsOnTime04 : DurationPoint {
        :>> mnemonic = "GNC_RCS_ON_TIME_04"; :>> pointId = 2047; :>> source = ApplicationName::gnc; :>> apidClass = ApidClass::guidance;
        :>> kind = TelemetryKind::engineering; :>> rate = 0.1 [Hz];
        :>> redLow = 0.0 [s]; :>> yellowLow = 0.0 [s]; :>> yellowHigh = 10000000.0 [s]; :>> redHigh = 100000000.0 [s];
    }
    item gncRcsOnTime05 : DurationPoint {
        :>> mnemonic = "GNC_RCS_ON_TIME_05"; :>> pointId = 2048; :>> source = ApplicationName::gnc; :>> apidClass = ApidClass::guidance;
        :>> kind = TelemetryKind::engineering; :>> rate = 0.1 [Hz];
        :>> redLow = 0.0 [s]; :>> yellowLow = 0.0 [s]; :>> yellowHigh = 10000000.0 [s]; :>> redHigh = 100000000.0 [s];
    }
    item gncRcsOnTime06 : DurationPoint {
        :>> mnemonic = "GNC_RCS_ON_TIME_06"; :>> pointId = 2049; :>> source = ApplicationName::gnc; :>> apidClass = ApidClass::guidance;
        :>> kind = TelemetryKind::engineering; :>> rate = 0.1 [Hz];
        :>> redLow = 0.0 [s]; :>> yellowLow = 0.0 [s]; :>> yellowHigh = 10000000.0 [s]; :>> redHigh = 100000000.0 [s];
    }
    item gncRcsOnTime07 : DurationPoint {
        :>> mnemonic = "GNC_RCS_ON_TIME_07"; :>> pointId = 2050; :>> source = ApplicationName::gnc; :>> apidClass = ApidClass::guidance;
        :>> kind = TelemetryKind::engineering; :>> rate = 0.1 [Hz];
        :>> redLow = 0.0 [s]; :>> yellowLow = 0.0 [s]; :>> yellowHigh = 10000000.0 [s]; :>> redHigh = 100000000.0 [s];
    }
    item gncRcsOnTime08 : DurationPoint {
        :>> mnemonic = "GNC_RCS_ON_TIME_08"; :>> pointId = 2051; :>> source = ApplicationName::gnc; :>> apidClass = ApidClass::guidance;
        :>> kind = TelemetryKind::engineering; :>> rate = 0.1 [Hz];
        :>> redLow = 0.0 [s]; :>> yellowLow = 0.0 [s]; :>> yellowHigh = 10000000.0 [s]; :>> redHigh = 100000000.0 [s];
    }
    item gncRcsPulses01 : CountPoint {
        :>> mnemonic = "GNC_RCS_PULSES_01"; :>> pointId = 2052; :>> source = ApplicationName::gnc; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item gncRcsPulses02 : CountPoint {
        :>> mnemonic = "GNC_RCS_PULSES_02"; :>> pointId = 2053; :>> source = ApplicationName::gnc; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item gncRcsPulses03 : CountPoint {
        :>> mnemonic = "GNC_RCS_PULSES_03"; :>> pointId = 2054; :>> source = ApplicationName::gnc; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item gncRcsPulses04 : CountPoint {
        :>> mnemonic = "GNC_RCS_PULSES_04"; :>> pointId = 2055; :>> source = ApplicationName::gnc; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item gncRcsPulses05 : CountPoint {
        :>> mnemonic = "GNC_RCS_PULSES_05"; :>> pointId = 2056; :>> source = ApplicationName::gnc; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item gncRcsPulses06 : CountPoint {
        :>> mnemonic = "GNC_RCS_PULSES_06"; :>> pointId = 2057; :>> source = ApplicationName::gnc; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item gncRcsPulses07 : CountPoint {
        :>> mnemonic = "GNC_RCS_PULSES_07"; :>> pointId = 2058; :>> source = ApplicationName::gnc; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item gncRcsPulses08 : CountPoint {
        :>> mnemonic = "GNC_RCS_PULSES_08"; :>> pointId = 2059; :>> source = ApplicationName::gnc; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item gncSunSensor01 : FractionPoint {
        :>> mnemonic = "GNC_SUN_SENSOR_01"; :>> pointId = 2060; :>> source = ApplicationName::gnc; :>> apidClass = ApidClass::guidance;
        :>> kind = TelemetryKind::engineering; :>> rate = 1.0 [Hz];
        :>> redLow = 0.0; :>> yellowLow = 0.1; :>> yellowHigh = 0.9; :>> redHigh = 1.0;
    }
    item gncSunSensor02 : FractionPoint {
        :>> mnemonic = "GNC_SUN_SENSOR_02"; :>> pointId = 2061; :>> source = ApplicationName::gnc; :>> apidClass = ApidClass::guidance;
        :>> kind = TelemetryKind::engineering; :>> rate = 1.0 [Hz];
        :>> redLow = 0.0; :>> yellowLow = 0.1; :>> yellowHigh = 0.9; :>> redHigh = 1.0;
    }
    item gncSunSensor03 : FractionPoint {
        :>> mnemonic = "GNC_SUN_SENSOR_03"; :>> pointId = 2062; :>> source = ApplicationName::gnc; :>> apidClass = ApidClass::guidance;
        :>> kind = TelemetryKind::engineering; :>> rate = 1.0 [Hz];
        :>> redLow = 0.0; :>> yellowLow = 0.1; :>> yellowHigh = 0.9; :>> redHigh = 1.0;
    }
    item gncSunSensor04 : FractionPoint {
        :>> mnemonic = "GNC_SUN_SENSOR_04"; :>> pointId = 2063; :>> source = ApplicationName::gnc; :>> apidClass = ApidClass::guidance;
        :>> kind = TelemetryKind::engineering; :>> rate = 1.0 [Hz];
        :>> redLow = 0.0; :>> yellowLow = 0.1; :>> yellowHigh = 0.9; :>> redHigh = 1.0;
    }
    item gncSunSensor05 : FractionPoint {
        :>> mnemonic = "GNC_SUN_SENSOR_05"; :>> pointId = 2064; :>> source = ApplicationName::gnc; :>> apidClass = ApidClass::guidance;
        :>> kind = TelemetryKind::engineering; :>> rate = 1.0 [Hz];
        :>> redLow = 0.0; :>> yellowLow = 0.1; :>> yellowHigh = 0.9; :>> redHigh = 1.0;
    }
    item gncSunSensor06 : FractionPoint {
        :>> mnemonic = "GNC_SUN_SENSOR_06"; :>> pointId = 2065; :>> source = ApplicationName::gnc; :>> apidClass = ApidClass::guidance;
        :>> kind = TelemetryKind::engineering; :>> rate = 1.0 [Hz];
        :>> redLow = 0.0; :>> yellowLow = 0.1; :>> yellowHigh = 0.9; :>> redHigh = 1.0;
    }
    item gncRangeToTarget : LengthPoint {
        :>> mnemonic = "GNC_RANGE_TO_TARGET"; :>> pointId = 2066; :>> source = ApplicationName::gnc; :>> apidClass = ApidClass::guidance;
        :>> kind = TelemetryKind::housekeeping; :>> rate = 1.0 [Hz];
        :>> redLow = 0.0 [m]; :>> yellowLow = 10.0 [m]; :>> yellowHigh = 100000000.0 [m]; :>> redHigh = 1000000000.0 [m];
    }
    item gncRangeRate : SpeedPoint {
        :>> mnemonic = "GNC_RANGE_RATE"; :>> pointId = 2067; :>> source = ApplicationName::gnc; :>> apidClass = ApidClass::guidance;
        :>> kind = TelemetryKind::housekeeping; :>> rate = 1.0 [Hz];
        :>> redLow = -100.0 [m/s]; :>> yellowLow = -50.0 [m/s]; :>> yellowHigh = 50.0 [m/s]; :>> redHigh = 100.0 [m/s];
    }
    item gncBearing01 : AnglePoint {
        :>> mnemonic = "GNC_BEARING_01"; :>> pointId = 2068; :>> source = ApplicationName::gnc; :>> apidClass = ApidClass::guidance;
        :>> kind = TelemetryKind::engineering; :>> rate = 1.0 [Hz];
        :>> redLow = -3.1416 [rad]; :>> yellowLow = -3.0 [rad]; :>> yellowHigh = 3.0 [rad]; :>> redHigh = 3.1416 [rad];
    }
    item gncBearing02 : AnglePoint {
        :>> mnemonic = "GNC_BEARING_02"; :>> pointId = 2069; :>> source = ApplicationName::gnc; :>> apidClass = ApidClass::guidance;
        :>> kind = TelemetryKind::engineering; :>> rate = 1.0 [Hz];
        :>> redLow = -3.1416 [rad]; :>> yellowLow = -3.0 [rad]; :>> yellowHigh = 3.0 [rad]; :>> redHigh = 3.1416 [rad];
    }
    item gncEphemerisAge : DurationPoint {
        :>> mnemonic = "GNC_EPHEMERIS_AGE"; :>> pointId = 2070; :>> source = ApplicationName::gnc; :>> apidClass = ApidClass::guidance;
        :>> kind = TelemetryKind::housekeeping; :>> rate = 0.1 [Hz];
        :>> redLow = 0.0 [s]; :>> yellowLow = 0.0 [s]; :>> yellowHigh = 2592000.0 [s]; :>> redHigh = 7776000.0 [s];
    }
    item gncGuidanceMode : StatusPoint {
        :>> mnemonic = "GNC_GUIDANCE_MODE"; :>> pointId = 2071; :>> source = ApplicationName::gnc; :>> apidClass = ApidClass::guidance;
        :>> kind = TelemetryKind::housekeeping; :>> rate = 1.0 [Hz];
        :>> redLow = 0; :>> yellowLow = 0; :>> yellowHigh = 254; :>> redHigh = 255;
    }
    item gncMomentum01 : FractionPoint {
        :>> mnemonic = "GNC_MOMENTUM_01"; :>> pointId = 2072; :>> source = ApplicationName::gnc; :>> apidClass = ApidClass::guidance;
        :>> kind = TelemetryKind::housekeeping; :>> rate = 1.0 [Hz];
        :>> redLow = -1.0; :>> yellowLow = -0.8; :>> yellowHigh = 0.8; :>> redHigh = 1.0;
    }
    item gncMomentum02 : FractionPoint {
        :>> mnemonic = "GNC_MOMENTUM_02"; :>> pointId = 2073; :>> source = ApplicationName::gnc; :>> apidClass = ApidClass::guidance;
        :>> kind = TelemetryKind::housekeeping; :>> rate = 1.0 [Hz];
        :>> redLow = -1.0; :>> yellowLow = -0.8; :>> yellowHigh = 0.8; :>> redHigh = 1.0;
    }
    item gncMomentum03 : FractionPoint {
        :>> mnemonic = "GNC_MOMENTUM_03"; :>> pointId = 2074; :>> source = ApplicationName::gnc; :>> apidClass = ApidClass::guidance;
        :>> kind = TelemetryKind::housekeeping; :>> rate = 1.0 [Hz];
        :>> redLow = -1.0; :>> yellowLow = -0.8; :>> yellowHigh = 0.8; :>> redHigh = 1.0;
    }
    item sepDischargeI01 : CurrentPoint {
        :>> mnemonic = "SEP_DISCHARGE_I_01"; :>> pointId = 3001; :>> source = ApplicationName::sepControl; :>> apidClass = ApidClass::propulsion;
        :>> kind = TelemetryKind::housekeeping; :>> rate = 1.0 [Hz];
        :>> redLow = 0.0 [A]; :>> yellowLow = 0.0 [A]; :>> yellowHigh = 30.0 [A]; :>> redHigh = 40.0 [A];
    }
    item sepDischargeI02 : CurrentPoint {
        :>> mnemonic = "SEP_DISCHARGE_I_02"; :>> pointId = 3002; :>> source = ApplicationName::sepControl; :>> apidClass = ApidClass::propulsion;
        :>> kind = TelemetryKind::housekeeping; :>> rate = 1.0 [Hz];
        :>> redLow = 0.0 [A]; :>> yellowLow = 0.0 [A]; :>> yellowHigh = 30.0 [A]; :>> redHigh = 40.0 [A];
    }
    item sepDischargeI03 : CurrentPoint {
        :>> mnemonic = "SEP_DISCHARGE_I_03"; :>> pointId = 3003; :>> source = ApplicationName::sepControl; :>> apidClass = ApidClass::propulsion;
        :>> kind = TelemetryKind::housekeeping; :>> rate = 1.0 [Hz];
        :>> redLow = 0.0 [A]; :>> yellowLow = 0.0 [A]; :>> yellowHigh = 30.0 [A]; :>> redHigh = 40.0 [A];
    }
    item sepDischargeV01 : VoltagePoint {
        :>> mnemonic = "SEP_DISCHARGE_V_01"; :>> pointId = 3004; :>> source = ApplicationName::sepControl; :>> apidClass = ApidClass::propulsion;
        :>> kind = TelemetryKind::housekeeping; :>> rate = 1.0 [Hz];
        :>> redLow = 0.0 [V]; :>> yellowLow = 200.0 [V]; :>> yellowHigh = 400.0 [V]; :>> redHigh = 450.0 [V];
    }
    item sepDischargeV02 : VoltagePoint {
        :>> mnemonic = "SEP_DISCHARGE_V_02"; :>> pointId = 3005; :>> source = ApplicationName::sepControl; :>> apidClass = ApidClass::propulsion;
        :>> kind = TelemetryKind::housekeeping; :>> rate = 1.0 [Hz];
        :>> redLow = 0.0 [V]; :>> yellowLow = 200.0 [V]; :>> yellowHigh = 400.0 [V]; :>> redHigh = 450.0 [V];
    }
    item sepDischargeV03 : VoltagePoint {
        :>> mnemonic = "SEP_DISCHARGE_V_03"; :>> pointId = 3006; :>> source = ApplicationName::sepControl; :>> apidClass = ApidClass::propulsion;
        :>> kind = TelemetryKind::housekeeping; :>> rate = 1.0 [Hz];
        :>> redLow = 0.0 [V]; :>> yellowLow = 200.0 [V]; :>> yellowHigh = 400.0 [V]; :>> redHigh = 450.0 [V];
    }
    item sepAnodeFlow01 : FractionPoint {
        :>> mnemonic = "SEP_ANODE_FLOW_01"; :>> pointId = 3007; :>> source = ApplicationName::sepControl; :>> apidClass = ApidClass::propulsion;
        :>> kind = TelemetryKind::engineering; :>> rate = 1.0 [Hz];
        :>> redLow = 0.0; :>> yellowLow = 0.1; :>> yellowHigh = 0.9; :>> redHigh = 1.0;
    }
    item sepAnodeFlow02 : FractionPoint {
        :>> mnemonic = "SEP_ANODE_FLOW_02"; :>> pointId = 3008; :>> source = ApplicationName::sepControl; :>> apidClass = ApidClass::propulsion;
        :>> kind = TelemetryKind::engineering; :>> rate = 1.0 [Hz];
        :>> redLow = 0.0; :>> yellowLow = 0.1; :>> yellowHigh = 0.9; :>> redHigh = 1.0;
    }
    item sepAnodeFlow03 : FractionPoint {
        :>> mnemonic = "SEP_ANODE_FLOW_03"; :>> pointId = 3009; :>> source = ApplicationName::sepControl; :>> apidClass = ApidClass::propulsion;
        :>> kind = TelemetryKind::engineering; :>> rate = 1.0 [Hz];
        :>> redLow = 0.0; :>> yellowLow = 0.1; :>> yellowHigh = 0.9; :>> redHigh = 1.0;
    }
    item sepCathodeFlow01 : FractionPoint {
        :>> mnemonic = "SEP_CATHODE_FLOW_01"; :>> pointId = 3010; :>> source = ApplicationName::sepControl; :>> apidClass = ApidClass::propulsion;
        :>> kind = TelemetryKind::engineering; :>> rate = 1.0 [Hz];
        :>> redLow = 0.0; :>> yellowLow = 0.1; :>> yellowHigh = 0.9; :>> redHigh = 1.0;
    }
    item sepCathodeFlow02 : FractionPoint {
        :>> mnemonic = "SEP_CATHODE_FLOW_02"; :>> pointId = 3011; :>> source = ApplicationName::sepControl; :>> apidClass = ApidClass::propulsion;
        :>> kind = TelemetryKind::engineering; :>> rate = 1.0 [Hz];
        :>> redLow = 0.0; :>> yellowLow = 0.1; :>> yellowHigh = 0.9; :>> redHigh = 1.0;
    }
    item sepCathodeFlow03 : FractionPoint {
        :>> mnemonic = "SEP_CATHODE_FLOW_03"; :>> pointId = 3012; :>> source = ApplicationName::sepControl; :>> apidClass = ApidClass::propulsion;
        :>> kind = TelemetryKind::engineering; :>> rate = 1.0 [Hz];
        :>> redLow = 0.0; :>> yellowLow = 0.1; :>> yellowHigh = 0.9; :>> redHigh = 1.0;
    }
    item sepKeeperI01 : CurrentPoint {
        :>> mnemonic = "SEP_KEEPER_I_01"; :>> pointId = 3013; :>> source = ApplicationName::sepControl; :>> apidClass = ApidClass::propulsion;
        :>> kind = TelemetryKind::engineering; :>> rate = 1.0 [Hz];
        :>> redLow = 0.0 [A]; :>> yellowLow = 0.0 [A]; :>> yellowHigh = 8.0 [A]; :>> redHigh = 10.0 [A];
    }
    item sepKeeperI02 : CurrentPoint {
        :>> mnemonic = "SEP_KEEPER_I_02"; :>> pointId = 3014; :>> source = ApplicationName::sepControl; :>> apidClass = ApidClass::propulsion;
        :>> kind = TelemetryKind::engineering; :>> rate = 1.0 [Hz];
        :>> redLow = 0.0 [A]; :>> yellowLow = 0.0 [A]; :>> yellowHigh = 8.0 [A]; :>> redHigh = 10.0 [A];
    }
    item sepKeeperI03 : CurrentPoint {
        :>> mnemonic = "SEP_KEEPER_I_03"; :>> pointId = 3015; :>> source = ApplicationName::sepControl; :>> apidClass = ApidClass::propulsion;
        :>> kind = TelemetryKind::engineering; :>> rate = 1.0 [Hz];
        :>> redLow = 0.0 [A]; :>> yellowLow = 0.0 [A]; :>> yellowHigh = 8.0 [A]; :>> redHigh = 10.0 [A];
    }
    item sepMagnetI01 : CurrentPoint {
        :>> mnemonic = "SEP_MAGNET_I_01"; :>> pointId = 3016; :>> source = ApplicationName::sepControl; :>> apidClass = ApidClass::propulsion;
        :>> kind = TelemetryKind::engineering; :>> rate = 1.0 [Hz];
        :>> redLow = 0.0 [A]; :>> yellowLow = 0.0 [A]; :>> yellowHigh = 8.0 [A]; :>> redHigh = 10.0 [A];
    }
    item sepMagnetI02 : CurrentPoint {
        :>> mnemonic = "SEP_MAGNET_I_02"; :>> pointId = 3017; :>> source = ApplicationName::sepControl; :>> apidClass = ApidClass::propulsion;
        :>> kind = TelemetryKind::engineering; :>> rate = 1.0 [Hz];
        :>> redLow = 0.0 [A]; :>> yellowLow = 0.0 [A]; :>> yellowHigh = 8.0 [A]; :>> redHigh = 10.0 [A];
    }
    item sepMagnetI03 : CurrentPoint {
        :>> mnemonic = "SEP_MAGNET_I_03"; :>> pointId = 3018; :>> source = ApplicationName::sepControl; :>> apidClass = ApidClass::propulsion;
        :>> kind = TelemetryKind::engineering; :>> rate = 1.0 [Hz];
        :>> redLow = 0.0 [A]; :>> yellowLow = 0.0 [A]; :>> yellowHigh = 8.0 [A]; :>> redHigh = 10.0 [A];
    }
    item sepCathodeHtrI01 : CurrentPoint {
        :>> mnemonic = "SEP_CATHODE_HTR_I_01"; :>> pointId = 3019; :>> source = ApplicationName::sepControl; :>> apidClass = ApidClass::propulsion;
        :>> kind = TelemetryKind::engineering; :>> rate = 1.0 [Hz];
        :>> redLow = 0.0 [A]; :>> yellowLow = 0.0 [A]; :>> yellowHigh = 8.0 [A]; :>> redHigh = 10.0 [A];
    }
    item sepCathodeHtrI02 : CurrentPoint {
        :>> mnemonic = "SEP_CATHODE_HTR_I_02"; :>> pointId = 3020; :>> source = ApplicationName::sepControl; :>> apidClass = ApidClass::propulsion;
        :>> kind = TelemetryKind::engineering; :>> rate = 1.0 [Hz];
        :>> redLow = 0.0 [A]; :>> yellowLow = 0.0 [A]; :>> yellowHigh = 8.0 [A]; :>> redHigh = 10.0 [A];
    }
    item sepCathodeHtrI03 : CurrentPoint {
        :>> mnemonic = "SEP_CATHODE_HTR_I_03"; :>> pointId = 3021; :>> source = ApplicationName::sepControl; :>> apidClass = ApidClass::propulsion;
        :>> kind = TelemetryKind::engineering; :>> rate = 1.0 [Hz];
        :>> redLow = 0.0 [A]; :>> yellowLow = 0.0 [A]; :>> yellowHigh = 8.0 [A]; :>> redHigh = 10.0 [A];
    }
    item sepThrusterT01 : TemperaturePoint {
        :>> mnemonic = "SEP_THRUSTER_T_01"; :>> pointId = 3022; :>> source = ApplicationName::sepControl; :>> apidClass = ApidClass::propulsion;
        :>> kind = TelemetryKind::engineering; :>> rate = 0.1 [Hz];
        :>> redLow = 233.0 [K]; :>> yellowLow = 253.0 [K]; :>> yellowHigh = 523.0 [K]; :>> redHigh = 573.0 [K];
    }
    item sepThrusterT02 : TemperaturePoint {
        :>> mnemonic = "SEP_THRUSTER_T_02"; :>> pointId = 3023; :>> source = ApplicationName::sepControl; :>> apidClass = ApidClass::propulsion;
        :>> kind = TelemetryKind::engineering; :>> rate = 0.1 [Hz];
        :>> redLow = 233.0 [K]; :>> yellowLow = 253.0 [K]; :>> yellowHigh = 523.0 [K]; :>> redHigh = 573.0 [K];
    }
    item sepThrusterT03 : TemperaturePoint {
        :>> mnemonic = "SEP_THRUSTER_T_03"; :>> pointId = 3024; :>> source = ApplicationName::sepControl; :>> apidClass = ApidClass::propulsion;
        :>> kind = TelemetryKind::engineering; :>> rate = 0.1 [Hz];
        :>> redLow = 233.0 [K]; :>> yellowLow = 253.0 [K]; :>> yellowHigh = 523.0 [K]; :>> redHigh = 573.0 [K];
    }
    item sepPpuInPower01 : PowerPoint {
        :>> mnemonic = "SEP_PPU_IN_POWER_01"; :>> pointId = 3025; :>> source = ApplicationName::sepControl; :>> apidClass = ApidClass::propulsion;
        :>> kind = TelemetryKind::housekeeping; :>> rate = 1.0 [Hz];
        :>> redLow = 0.0 [W]; :>> yellowLow = 0.0 [W]; :>> yellowHigh = 7000.0 [W]; :>> redHigh = 7500.0 [W];
    }
    item sepPpuInPower02 : PowerPoint {
        :>> mnemonic = "SEP_PPU_IN_POWER_02"; :>> pointId = 3026; :>> source = ApplicationName::sepControl; :>> apidClass = ApidClass::propulsion;
        :>> kind = TelemetryKind::housekeeping; :>> rate = 1.0 [Hz];
        :>> redLow = 0.0 [W]; :>> yellowLow = 0.0 [W]; :>> yellowHigh = 7000.0 [W]; :>> redHigh = 7500.0 [W];
    }
    item sepPpuInPower03 : PowerPoint {
        :>> mnemonic = "SEP_PPU_IN_POWER_03"; :>> pointId = 3027; :>> source = ApplicationName::sepControl; :>> apidClass = ApidClass::propulsion;
        :>> kind = TelemetryKind::housekeeping; :>> rate = 1.0 [Hz];
        :>> redLow = 0.0 [W]; :>> yellowLow = 0.0 [W]; :>> yellowHigh = 7000.0 [W]; :>> redHigh = 7500.0 [W];
    }
    item sepPpuT01 : TemperaturePoint {
        :>> mnemonic = "SEP_PPU_T_01"; :>> pointId = 3028; :>> source = ApplicationName::sepControl; :>> apidClass = ApidClass::propulsion;
        :>> kind = TelemetryKind::engineering; :>> rate = 0.1 [Hz];
        :>> redLow = 233.0 [K]; :>> yellowLow = 253.0 [K]; :>> yellowHigh = 313.0 [K]; :>> redHigh = 333.0 [K];
    }
    item sepPpuT02 : TemperaturePoint {
        :>> mnemonic = "SEP_PPU_T_02"; :>> pointId = 3029; :>> source = ApplicationName::sepControl; :>> apidClass = ApidClass::propulsion;
        :>> kind = TelemetryKind::engineering; :>> rate = 0.1 [Hz];
        :>> redLow = 233.0 [K]; :>> yellowLow = 253.0 [K]; :>> yellowHigh = 313.0 [K]; :>> redHigh = 333.0 [K];
    }
    item sepPpuT03 : TemperaturePoint {
        :>> mnemonic = "SEP_PPU_T_03"; :>> pointId = 3030; :>> source = ApplicationName::sepControl; :>> apidClass = ApidClass::propulsion;
        :>> kind = TelemetryKind::engineering; :>> rate = 0.1 [Hz];
        :>> redLow = 233.0 [K]; :>> yellowLow = 253.0 [K]; :>> yellowHigh = 313.0 [K]; :>> redHigh = 333.0 [K];
    }
    item sepPpuStatus01 : StatusPoint {
        :>> mnemonic = "SEP_PPU_STATUS_01"; :>> pointId = 3031; :>> source = ApplicationName::sepControl; :>> apidClass = ApidClass::propulsion;
        :>> kind = TelemetryKind::housekeeping; :>> rate = 1.0 [Hz];
        :>> redLow = 0; :>> yellowLow = 0; :>> yellowHigh = 254; :>> redHigh = 255;
    }
    item sepPpuStatus02 : StatusPoint {
        :>> mnemonic = "SEP_PPU_STATUS_02"; :>> pointId = 3032; :>> source = ApplicationName::sepControl; :>> apidClass = ApidClass::propulsion;
        :>> kind = TelemetryKind::housekeeping; :>> rate = 1.0 [Hz];
        :>> redLow = 0; :>> yellowLow = 0; :>> yellowHigh = 254; :>> redHigh = 255;
    }
    item sepPpuStatus03 : StatusPoint {
        :>> mnemonic = "SEP_PPU_STATUS_03"; :>> pointId = 3033; :>> source = ApplicationName::sepControl; :>> apidClass = ApidClass::propulsion;
        :>> kind = TelemetryKind::housekeeping; :>> rate = 1.0 [Hz];
        :>> redLow = 0; :>> yellowLow = 0; :>> yellowHigh = 254; :>> redHigh = 255;
    }
    item sepPpuEfficiency01 : FractionPoint {
        :>> mnemonic = "SEP_PPU_EFFICIENCY_01"; :>> pointId = 3034; :>> source = ApplicationName::sepControl; :>> apidClass = ApidClass::propulsion;
        :>> kind = TelemetryKind::engineering; :>> rate = 0.1 [Hz];
        :>> redLow = 0.0; :>> yellowLow = 0.1; :>> yellowHigh = 0.9; :>> redHigh = 1.0;
    }
    item sepPpuEfficiency02 : FractionPoint {
        :>> mnemonic = "SEP_PPU_EFFICIENCY_02"; :>> pointId = 3035; :>> source = ApplicationName::sepControl; :>> apidClass = ApidClass::propulsion;
        :>> kind = TelemetryKind::engineering; :>> rate = 0.1 [Hz];
        :>> redLow = 0.0; :>> yellowLow = 0.1; :>> yellowHigh = 0.9; :>> redHigh = 1.0;
    }
    item sepPpuEfficiency03 : FractionPoint {
        :>> mnemonic = "SEP_PPU_EFFICIENCY_03"; :>> pointId = 3036; :>> source = ApplicationName::sepControl; :>> apidClass = ApidClass::propulsion;
        :>> kind = TelemetryKind::engineering; :>> rate = 0.1 [Hz];
        :>> redLow = 0.0; :>> yellowLow = 0.1; :>> yellowHigh = 0.9; :>> redHigh = 1.0;
    }
    item sepTankP01 : PressurePoint {
        :>> mnemonic = "SEP_TANK_P_01"; :>> pointId = 3037; :>> source = ApplicationName::sepControl; :>> apidClass = ApidClass::propulsion;
        :>> kind = TelemetryKind::housekeeping; :>> rate = 0.1 [Hz];
        :>> redLow = 0.0 [Pa]; :>> yellowLow = 200000.0 [Pa]; :>> yellowHigh = 15000000.0 [Pa]; :>> redHigh = 18000000.0 [Pa];
    }
    item sepTankP02 : PressurePoint {
        :>> mnemonic = "SEP_TANK_P_02"; :>> pointId = 3038; :>> source = ApplicationName::sepControl; :>> apidClass = ApidClass::propulsion;
        :>> kind = TelemetryKind::housekeeping; :>> rate = 0.1 [Hz];
        :>> redLow = 0.0 [Pa]; :>> yellowLow = 200000.0 [Pa]; :>> yellowHigh = 15000000.0 [Pa]; :>> redHigh = 18000000.0 [Pa];
    }
    item sepTankT01 : TemperaturePoint {
        :>> mnemonic = "SEP_TANK_T_01"; :>> pointId = 3039; :>> source = ApplicationName::sepControl; :>> apidClass = ApidClass::propulsion;
        :>> kind = TelemetryKind::housekeeping; :>> rate = 0.1 [Hz];
        :>> redLow = 233.0 [K]; :>> yellowLow = 253.0 [K]; :>> yellowHigh = 313.0 [K]; :>> redHigh = 333.0 [K];
    }
    item sepTankT02 : TemperaturePoint {
        :>> mnemonic = "SEP_TANK_T_02"; :>> pointId = 3040; :>> source = ApplicationName::sepControl; :>> apidClass = ApidClass::propulsion;
        :>> kind = TelemetryKind::housekeeping; :>> rate = 0.1 [Hz];
        :>> redLow = 233.0 [K]; :>> yellowLow = 253.0 [K]; :>> yellowHigh = 313.0 [K]; :>> redHigh = 333.0 [K];
    }
    item sepXenonRemaining : MassPoint {
        :>> mnemonic = "SEP_XENON_REMAINING"; :>> pointId = 3041; :>> source = ApplicationName::sepControl; :>> apidClass = ApidClass::propulsion;
        :>> kind = TelemetryKind::housekeeping; :>> rate = 0.01 [Hz];
        :>> redLow = 0.0 [kg]; :>> yellowLow = 50.0 [kg]; :>> yellowHigh = 5000.0 [kg]; :>> redHigh = 6000.0 [kg];
    }
    item sepFlowTotal : MassPoint {
        :>> mnemonic = "SEP_FLOW_TOTAL"; :>> pointId = 3042; :>> source = ApplicationName::sepControl; :>> apidClass = ApidClass::propulsion;
        :>> kind = TelemetryKind::engineering; :>> rate = 0.01 [Hz];
        :>> redLow = 0.0 [kg]; :>> yellowLow = 10.0 [kg]; :>> yellowHigh = 2000.0 [kg]; :>> redHigh = 2500.0 [kg];
    }
    item sepRegP01 : PressurePoint {
        :>> mnemonic = "SEP_REG_P_01"; :>> pointId = 3043; :>> source = ApplicationName::sepControl; :>> apidClass = ApidClass::propulsion;
        :>> kind = TelemetryKind::housekeeping; :>> rate = 1.0 [Hz];
        :>> redLow = 0.0 [Pa]; :>> yellowLow = 100000.0 [Pa]; :>> yellowHigh = 300000.0 [Pa]; :>> redHigh = 350000.0 [Pa];
    }
    item sepRegP02 : PressurePoint {
        :>> mnemonic = "SEP_REG_P_02"; :>> pointId = 3044; :>> source = ApplicationName::sepControl; :>> apidClass = ApidClass::propulsion;
        :>> kind = TelemetryKind::housekeeping; :>> rate = 1.0 [Hz];
        :>> redLow = 0.0 [Pa]; :>> yellowLow = 100000.0 [Pa]; :>> yellowHigh = 300000.0 [Pa]; :>> redHigh = 350000.0 [Pa];
    }
    item sepLatchValve01 : StatusPoint {
        :>> mnemonic = "SEP_LATCH_VALVE_01"; :>> pointId = 3045; :>> source = ApplicationName::sepControl; :>> apidClass = ApidClass::propulsion;
        :>> kind = TelemetryKind::housekeeping; :>> rate = 1.0 [Hz];
        :>> redLow = 0; :>> yellowLow = 0; :>> yellowHigh = 1; :>> redHigh = 1;
    }
    item sepLatchValve02 : StatusPoint {
        :>> mnemonic = "SEP_LATCH_VALVE_02"; :>> pointId = 3046; :>> source = ApplicationName::sepControl; :>> apidClass = ApidClass::propulsion;
        :>> kind = TelemetryKind::housekeeping; :>> rate = 1.0 [Hz];
        :>> redLow = 0; :>> yellowLow = 0; :>> yellowHigh = 1; :>> redHigh = 1;
    }
    item sepLatchValve03 : StatusPoint {
        :>> mnemonic = "SEP_LATCH_VALVE_03"; :>> pointId = 3047; :>> source = ApplicationName::sepControl; :>> apidClass = ApidClass::propulsion;
        :>> kind = TelemetryKind::housekeeping; :>> rate = 1.0 [Hz];
        :>> redLow = 0; :>> yellowLow = 0; :>> yellowHigh = 1; :>> redHigh = 1;
    }
    item sepLatchValve04 : StatusPoint {
        :>> mnemonic = "SEP_LATCH_VALVE_04"; :>> pointId = 3048; :>> source = ApplicationName::sepControl; :>> apidClass = ApidClass::propulsion;
        :>> kind = TelemetryKind::housekeeping; :>> rate = 1.0 [Hz];
        :>> redLow = 0; :>> yellowLow = 0; :>> yellowHigh = 1; :>> redHigh = 1;
    }
    item sepLatchValve05 : StatusPoint {
        :>> mnemonic = "SEP_LATCH_VALVE_05"; :>> pointId = 3049; :>> source = ApplicationName::sepControl; :>> apidClass = ApidClass::propulsion;
        :>> kind = TelemetryKind::housekeeping; :>> rate = 1.0 [Hz];
        :>> redLow = 0; :>> yellowLow = 0; :>> yellowHigh = 1; :>> redHigh = 1;
    }
    item sepLatchValve06 : StatusPoint {
        :>> mnemonic = "SEP_LATCH_VALVE_06"; :>> pointId = 3050; :>> source = ApplicationName::sepControl; :>> apidClass = ApidClass::propulsion;
        :>> kind = TelemetryKind::housekeeping; :>> rate = 1.0 [Hz];
        :>> redLow = 0; :>> yellowLow = 0; :>> yellowHigh = 1; :>> redHigh = 1;
    }
    item sepGimbalAngle01 : AnglePoint {
        :>> mnemonic = "SEP_GIMBAL_ANGLE_01"; :>> pointId = 3051; :>> source = ApplicationName::sepControl; :>> apidClass = ApidClass::propulsion;
        :>> kind = TelemetryKind::engineering; :>> rate = 1.0 [Hz];
        :>> redLow = -0.25 [rad]; :>> yellowLow = -0.2 [rad]; :>> yellowHigh = 0.2 [rad]; :>> redHigh = 0.25 [rad];
    }
    item sepGimbalAngle02 : AnglePoint {
        :>> mnemonic = "SEP_GIMBAL_ANGLE_02"; :>> pointId = 3052; :>> source = ApplicationName::sepControl; :>> apidClass = ApidClass::propulsion;
        :>> kind = TelemetryKind::engineering; :>> rate = 1.0 [Hz];
        :>> redLow = -0.25 [rad]; :>> yellowLow = -0.2 [rad]; :>> yellowHigh = 0.2 [rad]; :>> redHigh = 0.25 [rad];
    }
    item sepGimbalAngle03 : AnglePoint {
        :>> mnemonic = "SEP_GIMBAL_ANGLE_03"; :>> pointId = 3053; :>> source = ApplicationName::sepControl; :>> apidClass = ApidClass::propulsion;
        :>> kind = TelemetryKind::engineering; :>> rate = 1.0 [Hz];
        :>> redLow = -0.25 [rad]; :>> yellowLow = -0.2 [rad]; :>> yellowHigh = 0.2 [rad]; :>> redHigh = 0.25 [rad];
    }
    item sepGimbalAngle04 : AnglePoint {
        :>> mnemonic = "SEP_GIMBAL_ANGLE_04"; :>> pointId = 3054; :>> source = ApplicationName::sepControl; :>> apidClass = ApidClass::propulsion;
        :>> kind = TelemetryKind::engineering; :>> rate = 1.0 [Hz];
        :>> redLow = -0.25 [rad]; :>> yellowLow = -0.2 [rad]; :>> yellowHigh = 0.2 [rad]; :>> redHigh = 0.25 [rad];
    }
    item sepGimbalAngle05 : AnglePoint {
        :>> mnemonic = "SEP_GIMBAL_ANGLE_05"; :>> pointId = 3055; :>> source = ApplicationName::sepControl; :>> apidClass = ApidClass::propulsion;
        :>> kind = TelemetryKind::engineering; :>> rate = 1.0 [Hz];
        :>> redLow = -0.25 [rad]; :>> yellowLow = -0.2 [rad]; :>> yellowHigh = 0.2 [rad]; :>> redHigh = 0.25 [rad];
    }
    item sepGimbalAngle06 : AnglePoint {
        :>> mnemonic = "SEP_GIMBAL_ANGLE_06"; :>> pointId = 3056; :>> source = ApplicationName::sepControl; :>> apidClass = ApidClass::propulsion;
        :>> kind = TelemetryKind::engineering; :>> rate = 1.0 [Hz];
        :>> redLow = -0.25 [rad]; :>> yellowLow = -0.2 [rad]; :>> yellowHigh = 0.2 [rad]; :>> redHigh = 0.25 [rad];
    }
    item sepThrustEst : ForcePoint {
        :>> mnemonic = "SEP_THRUST_EST"; :>> pointId = 3057; :>> source = ApplicationName::sepControl; :>> apidClass = ApidClass::propulsion;
        :>> kind = TelemetryKind::housekeeping; :>> rate = 1.0 [Hz];
        :>> redLow = 0.0 [N]; :>> yellowLow = 0.0 [N]; :>> yellowHigh = 1.0 [N]; :>> redHigh = 1.2 [N];
    }
    item sepIspEst : DurationPoint {
        :>> mnemonic = "SEP_ISP_EST"; :>> pointId = 3058; :>> source = ApplicationName::sepControl; :>> apidClass = ApidClass::propulsion;
        :>> kind = TelemetryKind::engineering; :>> rate = 0.1 [Hz];
        :>> redLow = 0.0 [s]; :>> yellowLow = 1500.0 [s]; :>> yellowHigh = 3000.0 [s]; :>> redHigh = 3500.0 [s];
    }
    item sepArcElapsed : DurationPoint {
        :>> mnemonic = "SEP_ARC_ELAPSED"; :>> pointId = 3059; :>> source = ApplicationName::sepControl; :>> apidClass = ApidClass::propulsion;
        :>> kind = TelemetryKind::housekeeping; :>> rate = 1.0 [Hz];
        :>> redLow = 0.0 [s]; :>> yellowLow = 0.0 [s]; :>> yellowHigh = 10000000.0 [s]; :>> redHigh = 100000000.0 [s];
    }
    item sepArcRemaining : DurationPoint {
        :>> mnemonic = "SEP_ARC_REMAINING"; :>> pointId = 3060; :>> source = ApplicationName::sepControl; :>> apidClass = ApidClass::propulsion;
        :>> kind = TelemetryKind::housekeeping; :>> rate = 1.0 [Hz];
        :>> redLow = 0.0 [s]; :>> yellowLow = 0.0 [s]; :>> yellowHigh = 10000000.0 [s]; :>> redHigh = 100000000.0 [s];
    }
    item epsBattCellV01 : VoltagePoint {
        :>> mnemonic = "EPS_BATT_CELL_V_01"; :>> pointId = 4001; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV02 : VoltagePoint {
        :>> mnemonic = "EPS_BATT_CELL_V_02"; :>> pointId = 4002; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV03 : VoltagePoint {
        :>> mnemonic = "EPS_BATT_CELL_V_03"; :>> pointId = 4003; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV04 : VoltagePoint {
        :>> mnemonic = "EPS_BATT_CELL_V_04"; :>> pointId = 4004; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV05 : VoltagePoint {
        :>> mnemonic = "EPS_BATT_CELL_V_05"; :>> pointId = 4005; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV06 : VoltagePoint {
        :>> mnemonic = "EPS_BATT_CELL_V_06"; :>> pointId = 4006; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV07 : VoltagePoint {
        :>> mnemonic = "EPS_BATT_CELL_V_07"; :>> pointId = 4007; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV08 : VoltagePoint {
        :>> mnemonic = "EPS_BATT_CELL_V_08"; :>> pointId = 4008; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV09 : VoltagePoint {
        :>> mnemonic = "EPS_BATT_CELL_V_09"; :>> pointId = 4009; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV10 : VoltagePoint {
        :>> mnemonic = "EPS_BATT_CELL_V_10"; :>> pointId = 4010; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV11 : VoltagePoint {
        :>> mnemonic = "EPS_BATT_CELL_V_11"; :>> pointId = 4011; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV12 : VoltagePoint {
        :>> mnemonic = "EPS_BATT_CELL_V_12"; :>> pointId = 4012; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV13 : VoltagePoint {
        :>> mnemonic = "EPS_BATT_CELL_V_13"; :>> pointId = 4013; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV14 : VoltagePoint {
        :>> mnemonic = "EPS_BATT_CELL_V_14"; :>> pointId = 4014; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV15 : VoltagePoint {
        :>> mnemonic = "EPS_BATT_CELL_V_15"; :>> pointId = 4015; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV16 : VoltagePoint {
        :>> mnemonic = "EPS_BATT_CELL_V_16"; :>> pointId = 4016; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV17 : VoltagePoint {
        :>> mnemonic = "EPS_BATT_CELL_V_17"; :>> pointId = 4017; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV18 : VoltagePoint {
        :>> mnemonic = "EPS_BATT_CELL_V_18"; :>> pointId = 4018; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV19 : VoltagePoint {
        :>> mnemonic = "EPS_BATT_CELL_V_19"; :>> pointId = 4019; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV20 : VoltagePoint {
        :>> mnemonic = "EPS_BATT_CELL_V_20"; :>> pointId = 4020; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV21 : VoltagePoint {
        :>> mnemonic = "EPS_BATT_CELL_V_21"; :>> pointId = 4021; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV22 : VoltagePoint {
        :>> mnemonic = "EPS_BATT_CELL_V_22"; :>> pointId = 4022; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV23 : VoltagePoint {
        :>> mnemonic = "EPS_BATT_CELL_V_23"; :>> pointId = 4023; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV24 : VoltagePoint {
        :>> mnemonic = "EPS_BATT_CELL_V_24"; :>> pointId = 4024; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV25 : VoltagePoint {
        :>> mnemonic = "EPS_BATT_CELL_V_25"; :>> pointId = 4025; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV26 : VoltagePoint {
        :>> mnemonic = "EPS_BATT_CELL_V_26"; :>> pointId = 4026; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV27 : VoltagePoint {
        :>> mnemonic = "EPS_BATT_CELL_V_27"; :>> pointId = 4027; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV28 : VoltagePoint {
        :>> mnemonic = "EPS_BATT_CELL_V_28"; :>> pointId = 4028; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV29 : VoltagePoint {
        :>> mnemonic = "EPS_BATT_CELL_V_29"; :>> pointId = 4029; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV30 : VoltagePoint {
        :>> mnemonic = "EPS_BATT_CELL_V_30"; :>> pointId = 4030; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV31 : VoltagePoint {
        :>> mnemonic = "EPS_BATT_CELL_V_31"; :>> pointId = 4031; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattCellV32 : VoltagePoint {
        :>> mnemonic = "EPS_BATT_CELL_V_32"; :>> pointId = 4032; :>> source = ApplicationName::powerManagement; :>> apidClass = ApidClass::housekeeping;
        :>> kind = TelemetryKind::engineering; :>> rate = 0.1 [Hz];
        :>> redLow = 2.5 [V]; :>> yellowLow = 3.0 [V]; :>> yellowHigh = 4.1 [V]; :>> redHigh = 4.25 [V];
    }
    item epsBattT01 : TemperaturePoint {
        :>> mnemonic = "EPS_BATT_T_01"; :>> pointId = 4033; :>> source = ApplicationName::powerManagement; :>> apidClass = ApidClass::housekeeping;
        :>> kind = TelemetryKind::housekeeping; :>> rate = 0.1 [Hz];
        :>> redLow = 263.0 [K]; :>> yellowLow = 273.0 [K]; :>> yellowHigh = 308.0 [K]; :>> redHigh = 318.0 [K];
    }
    item epsBattT02 : TemperaturePoint {
        :>> mnemonic = "EPS_BATT_T_02"; :>> pointId = 4034; :>> source = ApplicationName::powerManagement; :>> apidClass = ApidClass::housekeeping;
        :>> kind = TelemetryKind::housekeeping; :>> rate = 0.1 [Hz];
        :>> redLow = 263.0 [K]; :>> yellowLow = 273.0 [K]; :>> yellowHigh = 308.0 [K]; :>> redHigh = 318.0 [K];
    }
    item epsBattT03 : TemperaturePoint {
        :>> mnemonic = "EPS_BATT_T_03"; :>> pointId = 4035; :>> source = ApplicationName::powerManagement; :>> apidClass = ApidClass::housekeeping;
        :>> kind = TelemetryKind::housekeeping; :>> rate = 0.1 [Hz];
        :>> redLow = 263.0 [K]; :>> yellowLow = 273.0 [K]; :>> yellowHigh = 308.0 [K]; :>> redHigh = 318.0 [K];
    }
    item epsBattT04 : TemperaturePoint {
        :>> mnemonic = "EPS_BATT_T_04"; :>> pointId = 4036; :>> source = ApplicationName::powerManagement; :>> apidClass = ApidClass::housekeeping;
        :>> kind = TelemetryKind::housekeeping; :>> rate = 0.1 [Hz];
        :>> redLow = 263.0 [K]; :>> yellowLow = 273.0 [K]; :>> yellowHigh = 308.0 [K]; :>> redHigh = 318.0 [K];
    }
    item epsBattSoc01 : FractionPoint {
        :>> mnemonic = "EPS_BATT_SOC_01"; :>> pointId = 4037; :>> source = ApplicationName::powerManagement; :>> apidClass = ApidClass::housekeeping;
        :>> kind = TelemetryKind::housekeeping; :>> rate = 1.0 [Hz];
        :>> redLow = 0.3; :>> yellowLow = 0.4; :>> yellowHigh = 1.0; :>> redHigh = 1.0;
    }
    item epsBattSoc02 : FractionPoint {
        :>> mnemonic = "EPS_BATT_SOC_02"; :>> pointId = 4038; :>> source = ApplicationName::powerManagement; :>> apidClass = ApidClass::housekeeping;
        :>> kind = TelemetryKind::housekeeping; :>> rate = 1.0 [Hz];
        :>> redLow = 0.3; :>> yellowLow = 0.4; :>> yellowHigh = 1.0; :>> redHigh = 1.0;
    }
    item epsBattI01 : CurrentPoint {
        :>> mnemonic = "EPS_BATT_I_01"; :>> pointId = 4039; :>> source = ApplicationName::powerManagement; :>> apidClass = ApidClass::housekeeping;
        :>> kind = TelemetryKind::housekeeping; :>> rate = 1.0 [Hz];
        :>> redLow = -60.0 [A]; :>> yellowLow = -50.0 [A]; :>> yellowHigh = 50.0 [A]; :>> redHigh = 60.0 [A];
    }
    item epsBattI02 : CurrentPoint {
        :>> mnemonic = "EPS_BATT_I_02"; :>> pointId = 4040; :>> source = ApplicationName::powerManagement; :>> apidClass = ApidClass::housekeeping;
        :>> kind = TelemetryKind::housekeeping; :>> rate = 1.0 [Hz];
        :>> redLow = -60.0 [A]; :>> yellowLow = -50.0 [A]; :>> yellowHigh = 50.0 [A]; :>> redHigh = 60.0 [A];
    }
    item epsArrayStringI01 : CurrentPoint {
        :>> mnemonic = "EPS_ARRAY_STRING_I_01"; :>> pointId = 4041; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI02 : CurrentPoint {
        :>> mnemonic = "EPS_ARRAY_STRING_I_02"; :>> pointId = 4042; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI03 : CurrentPoint {
        :>> mnemonic = "EPS_ARRAY_STRING_I_03"; :>> pointId = 4043; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI04 : CurrentPoint {
        :>> mnemonic = "EPS_ARRAY_STRING_I_04"; :>> pointId = 4044; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI05 : CurrentPoint {
        :>> mnemonic = "EPS_ARRAY_STRING_I_05"; :>> pointId = 4045; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI06 : CurrentPoint {
        :>> mnemonic = "EPS_ARRAY_STRING_I_06"; :>> pointId = 4046; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI07 : CurrentPoint {
        :>> mnemonic = "EPS_ARRAY_STRING_I_07"; :>> pointId = 4047; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI08 : CurrentPoint {
        :>> mnemonic = "EPS_ARRAY_STRING_I_08"; :>> pointId = 4048; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI09 : CurrentPoint {
        :>> mnemonic = "EPS_ARRAY_STRING_I_09"; :>> pointId = 4049; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI10 : CurrentPoint {
        :>> mnemonic = "EPS_ARRAY_STRING_I_10"; :>> pointId = 4050; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI11 : CurrentPoint {
        :>> mnemonic = "EPS_ARRAY_STRING_I_11"; :>> pointId = 4051; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI12 : CurrentPoint {
        :>> mnemonic = "EPS_ARRAY_STRING_I_12"; :>> pointId = 4052; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI13 : CurrentPoint {
        :>> mnemonic = "EPS_ARRAY_STRING_I_13"; :>> pointId = 4053; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI14 : CurrentPoint {
        :>> mnemonic = "EPS_ARRAY_STRING_I_14"; :>> pointId = 4054; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI15 : CurrentPoint {
        :>> mnemonic = "EPS_ARRAY_STRING_I_15"; :>> pointId = 4055; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI16 : CurrentPoint {
        :>> mnemonic = "EPS_ARRAY_STRING_I_16"; :>> pointId = 4056; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI17 : CurrentPoint {
        :>> mnemonic = "EPS_ARRAY_STRING_I_17"; :>> pointId = 4057; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI18 : CurrentPoint {
        :>> mnemonic = "EPS_ARRAY_STRING_I_18"; :>> pointId = 4058; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI19 : CurrentPoint {
        :>> mnemonic = "EPS_ARRAY_STRING_I_19"; :>> pointId = 4059; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI20 : CurrentPoint {
        :>> mnemonic = "EPS_ARRAY_STRING_I_20"; :>> pointId = 4060; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI21 : CurrentPoint {
        :>> mnemonic = "EPS_ARRAY_STRING_I_21"; :>> pointId = 4061; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI22 : CurrentPoint {
        :>> mnemonic = "EPS_ARRAY_STRING_I_22"; :>> pointId = 4062; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI23 : CurrentPoint {
        :>> mnemonic = "EPS_ARRAY_STRING_I_23"; :>> pointId = 4063; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayStringI24 : CurrentPoint {
        :>> mnemonic = "EPS_ARRAY_STRING_I_24"; :>> pointId = 4064; :>> source = ApplicationName::powerManagement; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item epsArrayT01 : TemperaturePoint {
        :>> mnemonic = "EPS_ARRAY_T_01"; :>> pointId = 4065; :>> source = ApplicationName::powerManagement; :>> apidClass = ApidClass::housekeeping;
        :>> kind = TelemetryKind::engineering; :>> rate = 0.1 [Hz];
        :>> redLow = 173.0 [K]; :>> yellowLow = 193.0 [K]; :>> yellowHigh = 373.0 [K]; :>> redHigh = 393.0 [K];
    }
    item epsArrayT02 : TemperaturePoint {
        :>> mnemonic = "EPS_ARRAY_T_02"; :>> pointId = 4066; :>> source = ApplicationName::powerManagement; :>> apidClass = ApidClass::housekeeping;
        :>> kind = TelemetryKind::engineering; :>> rate = 0.1 [Hz];
        :>> redLow = 173.0 [K]; :>> yellowLow = 193.0 [K]; :>> yellowHigh = 373.0 [K]; :>> redHigh = 393.0 [K];
    }
    item epsArrayT03 : TemperaturePoint {
        :>> mnemonic = "EPS_ARRAY_T_03"; :>> pointId = 4067; :>> source = ApplicationName::powerManagement; :>> apidClass = ApidClass::housekeeping;
        :>> kind = TelemetryKind::engineering; :>> rate = 0.1 [Hz];
        :>> redLow = 173.0 [K]; :>> yellowLow = 193.0 [K]; :>> yellowHigh = 373.0 [K]; :>> redHigh = 393.0 [K];
    }
    item epsArrayT04 : TemperaturePoint {
        :>> mnemonic = "EPS_ARRAY_T_04"; :>> pointId = 4068; :>> source = ApplicationName::powerManagement; :>> apidClass = ApidClass::housekeeping;
        :>> kind = TelemetryKind::engineering; :>> rate = 0.1 [Hz];
        :>> redLow = 173.0 [K]; :>> yellowLow = 193.0 [K]; :>> yellowHigh = 373.0 [K]; :>> redHigh = 393.0 [K];
    }
    item epsArrayT05 : TemperaturePoint {
        :>> mnemonic = "EPS_ARRAY_T_05"; :>> pointId = 4069; :>> source = ApplicationName::powerManagement; :>> apidClass = ApidClass::housekeeping;
        :>> kind = TelemetryKind::engineering; :>> rate = 0.1 [Hz];
        :>> redLow = 173.0 [K]; :>> yellowLow = 193.0 [K]; :>> yellowHigh = 373.0 [K]; :>> redHigh = 393.0 [K];
    }
    item epsArrayT06 : TemperaturePoint {
        :>> mnemonic = "EPS_ARRAY_T_06"; :>> pointId = 4070; :>> source = ApplicationName::powerManagement; :>> apidClass = ApidClass::housekeeping;
        :>> kind = TelemetryKind::engineering; :>> rate = 0.1 [Hz];
        :>> redLow = 173.0 [K]; :>> yellowLow = 193.0 [K]; :>> yellowHigh = 373.0 [K]; :>> redHigh = 393.0 [K];
    }
    item epsArrayT07 : TemperaturePoint {
        :>> mnemonic = "EPS_ARRAY_T_07"; :>> pointId = 4071; :>> source = ApplicationName::powerManagement; :>> apidClass = ApidClass::housekeeping;
        :>> kind = TelemetryKind::engineering; :>> rate = 0.1 [Hz];
        :>> redLow = 173.0 [K]; :>> yellowLow = 193.0 [K]; :>> yellowHigh = 373.0 [K]; :>> redHigh = 393.0 [K];
    }
    item epsArrayT08 : TemperaturePoint {
        :>> mnemonic = "EPS_ARRAY_T_08"; :>> pointId = 4072; :>> source = ApplicationName::powerManagement; :>> apidClass = ApidClass::housekeeping;
        :>> kind = TelemetryKind::engineering; :>> rate = 0.1 [Hz];
        :>> redLow = 173.0 [K]; :>> yellowLow = 193.0 [K]; :>> yellowHigh = 373.0 [K]; :>> redHigh = 393.0 [K];
    }
    item epsArrayV01 : VoltagePoint {
        :>> mnemonic = "EPS_ARRAY_V_01"; :>> pointId = 4073; :>> source = ApplicationName::powerManagement; :>> apidClass = ApidClass::housekeeping;
        :>> kind = TelemetryKind::housekeeping; :>> rate = 1.0 [Hz];
        :>> redLow = 0.0 [V]; :>> yellowLow = 60.0 [V]; :>> yellowHigh = 120.0 [V]; :>> redHigh = 130.0 [V];
    }
    item epsArrayV02 : VoltagePoint {
        :>> mnemonic = "EPS_ARRAY_V_02"; :>> pointId = 4074; :>> source = ApplicationName::powerManagement; :>> apidClass = ApidClass::housekeeping;
        :>> kind = TelemetryKind::housekeeping; :>> rate = 1.0 [Hz];
        :>> redLow = 0.0 [V]; :>> yellowLow = 60.0 [V]; :>> yellowHigh = 120.0 [V]; :>> redHigh = 130.0 [V];
    }
    item epsArrayV03 : VoltagePoint {
        :>> mnemonic = "EPS_ARRAY_V_03"; :>> pointId = 4075; :>> source = ApplicationName::powerManagement; :>> apidClass = ApidClass::housekeeping;
        :>> kind = TelemetryKind::housekeeping; :>> rate = 1.0 [Hz];
        :>> redLow = 0.0 [V]; :>> yellowLow = 60.0 [V]; :>> yellowHigh = 120.0 [V]; :>> redHigh = 130.0 [V];
    }
    item epsArrayV04 : VoltagePoint {
        :>> mnemonic = "EPS_ARRAY_V_04"; :>> pointId = 4076; :>> source = ApplicationName::powerManagement; :>> apidClass = ApidClass::housekeeping;
        :>> kind = TelemetryKind::housekeeping; :>> rate = 1.0 [Hz];
        :>> redLow = 0.0 [V]; :>> yellowLow = 60.0 [V]; :>> yellowHigh = 120.0 [V]; :>> redHigh = 130.0 [V];
    }
    item epsBusV01 : VoltagePoint {
        :>> mnemonic = "EPS_BUS_V_01"; :>> pointId = 4077; :>> source = ApplicationName::powerManagement; :>> apidClass = ApidClass::housekeeping;
        :>> kind = TelemetryKind::housekeeping; :>> rate = 1.0 [Hz];
        :>> redLow = 26.0 [V]; :>> yellowLow = 27.0 [V]; :>> yellowHigh = 29.0 [V]; :>> redHigh = 30.0 [V];
    }
    item epsBusV02 : VoltagePoint {
        :>> mnemonic = "EPS_BUS_V_02"; :>> pointId = 4078; :>> source = ApplicationName::powerManagement; :>> apidClass = ApidClass::housekeeping;
        :>> kind = TelemetryKind::housekeeping; :>> rate = 1.0 [Hz];
        :>> redLow = 26.0 [V]; :>> yellowLow = 27.0 [V]; :>> yellowHigh = 29.0 [V]; :>> redHigh = 30.0 [V];
    }
    item epsBusI01 : CurrentPoint {
        :>> mnemonic = "EPS_BUS_I_01"; :>> pointId = 4079; :>> source = ApplicationName::powerManagement; :>> apidClass = ApidClass::housekeeping;
        :>> kind = TelemetryKind::housekeeping; :>> rate = 1.0 [Hz];
        :>> redLow = 0.0 [A]; :>> yellowLow = 0.0 [A]; :>> yellowHigh = 150.0 [A]; :>> redHigh = 180.0 [A];
    }
    item epsBusI02 : CurrentPoint {
        :>> mnemonic = "EPS_BUS_I_02"; :>> pointId = 4080; :>> source = ApplicationName::powerManagement; :>> apidClass = ApidClass::housekeeping;
        :>> kind = TelemetryKind::housekeeping; :>> rate = 1.0 [Hz];
        :>> redLow = 0.0 [A]; :>> yellowLow = 0.0 [A]; :>> yellowHigh = 150.0 [A]; :>> redHigh = 180.0 [A];
    }
    item epsSwState01 : StatusPoint {
        :>> mnemonic = "EPS_SW_STATE_01"; :>> pointId = 4081; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState02 : StatusPoint {
        :>> mnemonic = "EPS_SW_STATE_02"; :>> pointId = 4082; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState03 : StatusPoint {
        :>> mnemonic = "EPS_SW_STATE_03"; :>> pointId = 4083; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState04 : StatusPoint {
        :>> mnemonic = "EPS_SW_STATE_04"; :>> pointId = 4084; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState05 : StatusPoint {
        :>> mnemonic = "EPS_SW_STATE_05"; :>> pointId = 4085; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState06 : StatusPoint {
        :>> mnemonic = "EPS_SW_STATE_06"; :>> pointId = 4086; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState07 : StatusPoint {
        :>> mnemonic = "EPS_SW_STATE_07"; :>> pointId = 4087; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState08 : StatusPoint {
        :>> mnemonic = "EPS_SW_STATE_08"; :>> pointId = 4088; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState09 : StatusPoint {
        :>> mnemonic = "EPS_SW_STATE_09"; :>> pointId = 4089; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState10 : StatusPoint {
        :>> mnemonic = "EPS_SW_STATE_10"; :>> pointId = 4090; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState11 : StatusPoint {
        :>> mnemonic = "EPS_SW_STATE_11"; :>> pointId = 4091; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState12 : StatusPoint {
        :>> mnemonic = "EPS_SW_STATE_12"; :>> pointId = 4092; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState13 : StatusPoint {
        :>> mnemonic = "EPS_SW_STATE_13"; :>> pointId = 4093; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState14 : StatusPoint {
        :>> mnemonic = "EPS_SW_STATE_14"; :>> pointId = 4094; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState15 : StatusPoint {
        :>> mnemonic = "EPS_SW_STATE_15"; :>> pointId = 4095; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState16 : StatusPoint {
        :>> mnemonic = "EPS_SW_STATE_16"; :>> pointId = 4096; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState17 : StatusPoint {
        :>> mnemonic = "EPS_SW_STATE_17"; :>> pointId = 4097; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState18 : StatusPoint {
        :>> mnemonic = "EPS_SW_STATE_18"; :>> pointId = 4098; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState19 : StatusPoint {
        :>> mnemonic = "EPS_SW_STATE_19"; :>> pointId = 4099; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState20 : StatusPoint {
        :>> mnemonic = "EPS_SW_STATE_20"; :>> pointId = 4100; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState21 : StatusPoint {
        :>> mnemonic = "EPS_SW_STATE_21"; :>> pointId = 4101; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState22 : StatusPoint {
        :>> mnemonic = "EPS_SW_STATE_22"; :>> pointId = 4102; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState23 : StatusPoint {
        :>> mnemonic = "EPS_SW_STATE_23"; :>> pointId = 4103; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwState24 : StatusPoint {
        :>> mnemonic = "EPS_SW_STATE_24"; :>> pointId = 4104; :>> source = ApplicationName::powerManagement; :>> apidClass = ApidClass::housekeeping;
        :>> kind = TelemetryKind::housekeeping; :>> rate = 1.0 [Hz];
        :>> redLow = 0; :>> yellowLow = 0; :>> yellowHigh = 1; :>> redHigh = 1;
    }
    item epsSwI01 : CurrentPoint {
        :>> mnemonic = "EPS_SW_I_01"; :>> pointId = 4105; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI02 : CurrentPoint {
        :>> mnemonic = "EPS_SW_I_02"; :>> pointId = 4106; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI03 : CurrentPoint {
        :>> mnemonic = "EPS_SW_I_03"; :>> pointId = 4107; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI04 : CurrentPoint {
        :>> mnemonic = "EPS_SW_I_04"; :>> pointId = 4108; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI05 : CurrentPoint {
        :>> mnemonic = "EPS_SW_I_05"; :>> pointId = 4109; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI06 : CurrentPoint {
        :>> mnemonic = "EPS_SW_I_06"; :>> pointId = 4110; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI07 : CurrentPoint {
        :>> mnemonic = "EPS_SW_I_07"; :>> pointId = 4111; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI08 : CurrentPoint {
        :>> mnemonic = "EPS_SW_I_08"; :>> pointId = 4112; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI09 : CurrentPoint {
        :>> mnemonic = "EPS_SW_I_09"; :>> pointId = 4113; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI10 : CurrentPoint {
        :>> mnemonic = "EPS_SW_I_10"; :>> pointId = 4114; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI11 : CurrentPoint {
        :>> mnemonic = "EPS_SW_I_11"; :>> pointId = 4115; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI12 : CurrentPoint {
        :>> mnemonic = "EPS_SW_I_12"; :>> pointId = 4116; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI13 : CurrentPoint {
        :>> mnemonic = "EPS_SW_I_13"; :>> pointId = 4117; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI14 : CurrentPoint {
        :>> mnemonic = "EPS_SW_I_14"; :>> pointId = 4118; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI15 : CurrentPoint {
        :>> mnemonic = "EPS_SW_I_15"; :>> pointId = 4119; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI16 : CurrentPoint {
        :>> mnemonic = "EPS_SW_I_16"; :>> pointId = 4120; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI17 : CurrentPoint {
        :>> mnemonic = "EPS_SW_I_17"; :>> pointId = 4121; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI18 : CurrentPoint {
        :>> mnemonic = "EPS_SW_I_18"; :>> pointId = 4122; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI19 : CurrentPoint {
        :>> mnemonic = "EPS_SW_I_19"; :>> pointId = 4123; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI20 : CurrentPoint {
        :>> mnemonic = "EPS_SW_I_20"; :>> pointId = 4124; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI21 : CurrentPoint {
        :>> mnemonic = "EPS_SW_I_21"; :>> pointId = 4125; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI22 : CurrentPoint {
        :>> mnemonic = "EPS_SW_I_22"; :>> pointId = 4126; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI23 : CurrentPoint {
        :>> mnemonic = "EPS_SW_I_23"; :>> pointId = 4127; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSwI24 : CurrentPoint {
        :>> mnemonic = "EPS_SW_I_24"; :>> pointId = 4128; :>> source = ApplicationName::powerManagement; :>> apidClass = ApidClass::housekeeping;
        :>> kind = TelemetryKind::engineering; :>> rate = 1.0 [Hz];
        :>> redLow = 0.0 [A]; :>> yellowLow = 0.0 [A]; :>> yellowHigh = 8.0 [A]; :>> redHigh = 10.0 [A];
    }
    item epsSadaAngle01 : AnglePoint {
        :>> mnemonic = "EPS_SADA_ANGLE_01"; :>> pointId = 4129; :>> source = ApplicationName::powerManagement; :>> apidClass = ApidClass::housekeeping;
        :>> kind = TelemetryKind::housekeeping; :>> rate = 1.0 [Hz];
        :>> redLow = -3.1416 [rad]; :>> yellowLow = -3.0 [rad]; :>> yellowHigh = 3.0 [rad]; :>> redHigh = 3.1416 [rad];
    }
    item epsSadaAngle02 : AnglePoint {
        :>> mnemonic = "EPS_SADA_ANGLE_02"; :>> pointId = 4130; :>> source = ApplicationName::powerManagement; :>> apidClass = ApidClass::housekeeping;
        :>> kind = TelemetryKind::housekeeping; :>> rate = 1.0 [Hz];
        :>> redLow = -3.1416 [rad]; :>> yellowLow = -3.0 [rad]; :>> yellowHigh = 3.0 [rad]; :>> redHigh = 3.1416 [rad];
    }
    item epsSadaRate01 : AngularRatePoint {
        :>> mnemonic = "EPS_SADA_RATE_01"; :>> pointId = 4131; :>> source = ApplicationName::powerManagement; :>> apidClass = ApidClass::housekeeping;
        :>> kind = TelemetryKind::engineering; :>> rate = 1.0 [Hz];
        :>> redLow = -0.1 [rad/s]; :>> yellowLow = -0.05 [rad/s]; :>> yellowHigh = 0.05 [rad/s]; :>> redHigh = 0.1 [rad/s];
    }
    item epsSadaRate02 : AngularRatePoint {
        :>> mnemonic = "EPS_SADA_RATE_02"; :>> pointId = 4132; :>> source = ApplicationName::powerManagement; :>> apidClass = ApidClass::housekeeping;
        :>> kind = TelemetryKind::engineering; :>> rate = 1.0 [Hz];
        :>> redLow = -0.1 [rad/s]; :>> yellowLow = -0.05 [rad/s]; :>> yellowHigh = 0.05 [rad/s]; :>> redHigh = 0.1 [rad/s];
    }
    item epsPcuT01 : TemperaturePoint {
        :>> mnemonic = "EPS_PCU_T_01"; :>> pointId = 4133; :>> source = ApplicationName::powerManagement; :>> apidClass = ApidClass::housekeeping;
        :>> kind = TelemetryKind::housekeeping; :>> rate = 0.1 [Hz];
        :>> redLow = 233.0 [K]; :>> yellowLow = 253.0 [K]; :>> yellowHigh = 313.0 [K]; :>> redHigh = 333.0 [K];
    }
    item epsPcuT02 : TemperaturePoint {
        :>> mnemonic = "EPS_PCU_T_02"; :>> pointId = 4134; :>> source = ApplicationName::powerManagement; :>> apidClass = ApidClass::housekeeping;
        :>> kind = TelemetryKind::housekeeping; :>> rate = 0.1 [Hz];
        :>> redLow = 233.0 [K]; :>> yellowLow = 253.0 [K]; :>> yellowHigh = 313.0 [K]; :>> redHigh = 333.0 [K];
    }
    item epsLoadShedLevel : StatusPoint {
        :>> mnemonic = "EPS_LOAD_SHED_LEVEL"; :>> pointId = 4135; :>> source = ApplicationName::powerManagement; :>> apidClass = ApidClass::housekeeping;
        :>> kind = TelemetryKind::housekeeping; :>> rate = 1.0 [Hz];
        :>> redLow = 0; :>> yellowLow = 0; :>> yellowHigh = 3; :>> redHigh = 3;
    }
    item epsTotalLoad : PowerPoint {
        :>> mnemonic = "EPS_TOTAL_LOAD"; :>> pointId = 4136; :>> source = ApplicationName::powerManagement; :>> apidClass = ApidClass::housekeeping;
        :>> kind = TelemetryKind::housekeeping; :>> rate = 1.0 [Hz];
        :>> redLow = 0.0 [W]; :>> yellowLow = 0.0 [W]; :>> yellowHigh = 9000.0 [W]; :>> redHigh = 10000.0 [W];
    }
    item epsArrayPower : PowerPoint {
        :>> mnemonic = "EPS_ARRAY_POWER"; :>> pointId = 4137; :>> source = ApplicationName::powerManagement; :>> apidClass = ApidClass::housekeeping;
        :>> kind = TelemetryKind::housekeeping; :>> rate = 1.0 [Hz];
        :>> redLow = 0.0 [W]; :>> yellowLow = 0.0 [W]; :>> yellowHigh = 12000.0 [W]; :>> redHigh = 13000.0 [W];
    }
    item thmZoneT01 : TemperaturePoint {
        :>> mnemonic = "THM_ZONE_T_01"; :>> pointId = 5001; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT02 : TemperaturePoint {
        :>> mnemonic = "THM_ZONE_T_02"; :>> pointId = 5002; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT03 : TemperaturePoint {
        :>> mnemonic = "THM_ZONE_T_03"; :>> pointId = 5003; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT04 : TemperaturePoint {
        :>> mnemonic = "THM_ZONE_T_04"; :>> pointId = 5004; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT05 : TemperaturePoint {
        :>> mnemonic = "THM_ZONE_T_05"; :>> pointId = 5005; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT06 : TemperaturePoint {
        :>> mnemonic = "THM_ZONE_T_06"; :>> pointId = 5006; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT07 : TemperaturePoint {
        :>> mnemonic = "THM_ZONE_T_07"; :>> pointId = 5007; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT08 : TemperaturePoint {
        :>> mnemonic = "THM_ZONE_T_08"; :>> pointId = 5008; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT09 : TemperaturePoint {
        :>> mnemonic = "THM_ZONE_T_09"; :>> pointId = 5009; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT10 : TemperaturePoint {
        :>> mnemonic = "THM_ZONE_T_10"; :>> pointId = 5010; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT11 : TemperaturePoint {
        :>> mnemonic = "THM_ZONE_T_11"; :>> pointId = 5011; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT12 : TemperaturePoint {
        :>> mnemonic = "THM_ZONE_T_12"; :>> pointId = 5012; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT13 : TemperaturePoint {
        :>> mnemonic = "THM_ZONE_T_13"; :>> pointId = 5013; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT14 : TemperaturePoint {
        :>> mnemonic = "THM_ZONE_T_14"; :>> pointId = 5014; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT15 : TemperaturePoint {
        :>> mnemonic = "THM_ZONE_T_15"; :>> pointId = 5015; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT16 : TemperaturePoint {
        :>> mnemonic = "THM_ZONE_T_16"; :>> pointId = 5016; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT17 : TemperaturePoint {
        :>> mnemonic = "THM_ZONE_T_17"; :>> pointId = 5017; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT18 : TemperaturePoint {
        :>> mnemonic = "THM_ZONE_T_18"; :>> pointId = 5018; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT19 : TemperaturePoint {
        :>> mnemonic = "THM_ZONE_T_19"; :>> pointId = 5019; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT20 : TemperaturePoint {
        :>> mnemonic = "THM_ZONE_T_20"; :>> pointId = 5020; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT21 : TemperaturePoint {
        :>> mnemonic = "THM_ZONE_T_21"; :>> pointId = 5021; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT22 : TemperaturePoint {
        :>> mnemonic = "THM_ZONE_T_22"; :>> pointId = 5022; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT23 : TemperaturePoint {
        :>> mnemonic = "THM_ZONE_T_23"; :>> pointId = 5023; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT24 : TemperaturePoint {
        :>> mnemonic = "THM_ZONE_T_24"; :>> pointId = 5024; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT25 : TemperaturePoint {
        :>> mnemonic = "THM_ZONE_T_25"; :>> pointId = 5025; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT26 : TemperaturePoint {
        :>> mnemonic = "THM_ZONE_T_26"; :>> pointId = 5026; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT27 : TemperaturePoint {
        :>> mnemonic = "THM_ZONE_T_27"; :>> pointId = 5027; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT28 : TemperaturePoint {
        :>> mnemonic = "THM_ZONE_T_28"; :>> pointId = 5028; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT29 : TemperaturePoint {
        :>> mnemonic = "THM_ZONE_T_29"; :>> pointId = 5029; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT30 : TemperaturePoint {
        :>> mnemonic = "THM_ZONE_T_30"; :>> pointId = 5030; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT31 : TemperaturePoint {
        :>> mnemonic = "THM_ZONE_T_31"; :>> pointId = 5031; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT32 : TemperaturePoint {
        :>> mnemonic = "THM_ZONE_T_32"; :>> pointId = 5032; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT33 : TemperaturePoint {
        :>> mnemonic = "THM_ZONE_T_33"; :>> pointId = 5033; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT34 : TemperaturePoint {
        :>> mnemonic = "THM_ZONE_T_34"; :>> pointId = 5034; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT35 : TemperaturePoint {
        :>> mnemonic = "THM_ZONE_T_35"; :>> pointId = 5035; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT36 : TemperaturePoint {
        :>> mnemonic = "THM_ZONE_T_36"; :>> pointId = 5036; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT37 : TemperaturePoint {
        :>> mnemonic = "THM_ZONE_T_37"; :>> pointId = 5037; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT38 : TemperaturePoint {
        :>> mnemonic = "THM_ZONE_T_38"; :>> pointId = 5038; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT39 : TemperaturePoint {
        :>> mnemonic = "THM_ZONE_T_39"; :>> pointId = 5039; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT40 : TemperaturePoint {
        :>> mnemonic = "THM_ZONE_T_40"; :>> pointId = 5040; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT41 : TemperaturePoint {
        :>> mnemonic = "THM_ZONE_T_41"; :>> pointId = 5041; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT42 : TemperaturePoint {
        :>> mnemonic = "THM_ZONE_T_42"; :>> pointId = 5042; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT43 : TemperaturePoint {
        :>> mnemonic = "THM_ZONE_T_43"; :>> pointId = 5043; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT44 : TemperaturePoint {
        :>> mnemonic = "THM_ZONE_T_44"; :>> pointId = 5044; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT45 : TemperaturePoint {
        :>> mnemonic = "THM_ZONE_T_45"; :>> pointId = 5045; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT46 : TemperaturePoint {
        :>> mnemonic = "THM_ZONE_T_46"; :>> pointId = 5046; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT47 : TemperaturePoint {
        :>> mnemonic = "THM_ZONE_T_47"; :>> pointId = 5047; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT48 : TemperaturePoint {
        :>> mnemonic = "THM_ZONE_T_48"; :>> pointId = 5048; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT49 : TemperaturePoint {
        :>> mnemonic = "THM_ZONE_T_49"; :>> pointId = 5049; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT50 : TemperaturePoint {
        :>> mnemonic = "THM_ZONE_T_50"; :>> pointId = 5050; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT51 : TemperaturePoint {
        :>> mnemonic = "THM_ZONE_T_51"; :>> pointId = 5051; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT52 : TemperaturePoint {
        :>> mnemonic = "THM_ZONE_T_52"; :>> pointId = 5052; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT53 : TemperaturePoint {
        :>> mnemonic = "THM_ZONE_T_53"; :>> pointId = 5053; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT54 : TemperaturePoint {
        :>> mnemonic = "THM_ZONE_T_54"; :>> pointId = 5054; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT55 : TemperaturePoint {
        :>> mnemonic = "THM_ZONE_T_55"; :>> pointId = 5055; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT56 : TemperaturePoint {
        :>> mnemonic = "THM_ZONE_T_56"; :>> pointId = 5056; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT57 : TemperaturePoint {
        :>> mnemonic = "THM_ZONE_T_57"; :>> pointId = 5057; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT58 : TemperaturePoint {
        :>> mnemonic = "THM_ZONE_T_58"; :>> pointId = 5058; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT59 : TemperaturePoint {
        :>> mnemonic = "THM_ZONE_T_59"; :>> pointId = 5059; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT60 : TemperaturePoint {
        :>> mnemonic = "THM_ZONE_T_60"; :>> pointId = 5060; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT61 : TemperaturePoint {
        :>> mnemonic = "THM_ZONE_T_61"; :>> pointId = 5061; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT62 : TemperaturePoint {
        :>> mnemonic = "THM_ZONE_T_62"; :>> pointId = 5062; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT63 : TemperaturePoint {
        :>> mnemonic = "THM_ZONE_T_63"; :>> pointId = 5063; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT64 : TemperaturePoint {
        :>> mnemonic = "THM_ZONE_T_64"; :>> pointId = 5064; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT65 : TemperaturePoint {
        :>> mnemonic = "THM_ZONE_T_65"; :>> pointId = 5065; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT66 : TemperaturePoint {
        :>> mnemonic = "THM_ZONE_T_66"; :>> pointId = 5066; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT67 : TemperaturePoint {
        :>> mnemonic = "THM_ZONE_T_67"; :>> pointId = 5067; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT68 : TemperaturePoint {
        :>> mnemonic = "THM_ZONE_T_68"; :>> pointId = 5068; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT69 : TemperaturePoint {
        :>> mnemonic = "THM_ZONE_T_69"; :>> pointId = 5069; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT70 : TemperaturePoint {
        :>> mnemonic = "THM_ZONE_T_70"; :>> pointId = 5070; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT71 : TemperaturePoint {
        :>> mnemonic = "THM_ZONE_T_71"; :>> pointId = 5071; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT72 : TemperaturePoint {
        :>> mnemonic = "THM_ZONE_T_72"; :>> pointId = 5072; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT73 : TemperaturePoint {
        :>> mnemonic = "THM_ZONE_T_73"; :>> pointId = 5073; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT74 : TemperaturePoint {
        :>> mnemonic = "THM_ZONE_T_74"; :>> pointId = 5074; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT75 : TemperaturePoint {
        :>> mnemonic = "THM_ZONE_T_75"; :>> pointId = 5075; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT76 : TemperaturePoint {
        :>> mnemonic = "THM_ZONE_T_76"; :>> pointId = 5076; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT77 : TemperaturePoint {
        :>> mnemonic = "THM_ZONE_T_77"; :>> pointId = 5077; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT78 : TemperaturePoint {
        :>> mnemonic = "THM_ZONE_T_78"; :>> pointId = 5078; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT79 : TemperaturePoint {
        :>> mnemonic = "THM_ZONE_T_79"; :>> pointId = 5079; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT80 : TemperaturePoint {
        :>> mnemonic = "THM_ZONE_T_80"; :>> pointId = 5080; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT81 : TemperaturePoint {
        :>> mnemonic = "THM_ZONE_T_81"; :>> pointId = 5081; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT82 : TemperaturePoint {
        :>> mnemonic = "THM_ZONE_T_82"; :>> pointId = 5082; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT83 : TemperaturePoint {
        :>> mnemonic = "THM_ZONE_T_83"; :>> pointId = 5083; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT84 : TemperaturePoint {
        :>> mnemonic = "THM_ZONE_T_84"; :>> pointId = 5084; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT85 : TemperaturePoint {
        :>> mnemonic = "THM_ZONE_T_85"; :>> pointId = 5085; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT86 : TemperaturePoint {
        :>> mnemonic = "THM_ZONE_T_86"; :>> pointId = 5086; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT87 : TemperaturePoint {
        :>> mnemonic = "THM_ZONE_T_87"; :>> pointId = 5087; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT88 : TemperaturePoint {
        :>> mnemonic = "THM_ZONE_T_88"; :>> pointId = 5088; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT89 : TemperaturePoint {
        :>> mnemonic = "THM_ZONE_T_89"; :>> pointId = 5089; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT90 : TemperaturePoint {
        :>> mnemonic = "THM_ZONE_T_90"; :>> pointId = 5090; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT91 : TemperaturePoint {
        :>> mnemonic = "THM_ZONE_T_91"; :>> pointId = 5091; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT92 : TemperaturePoint {
        :>> mnemonic = "THM_ZONE_T_92"; :>> pointId = 5092; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT93 : TemperaturePoint {
        :>> mnemonic = "THM_ZONE_T_93"; :>> pointId = 5093; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT94 : TemperaturePoint {
        :>> mnemonic = "THM_ZONE_T_94"; :>> pointId = 5094; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT95 : TemperaturePoint {
        :>> mnemonic = "THM_ZONE_T_95"; :>> pointId = 5095; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT96 : TemperaturePoint {
        :>> mnemonic = "THM_ZONE_T_96"; :>> pointId = 5096; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT97 : TemperaturePoint {
        :>> mnemonic = "THM_ZONE_T_97"; :>> pointId = 5097; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT98 : TemperaturePoint {
        :>> mnemonic = "THM_ZONE_T_98"; :>> pointId = 5098; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT99 : TemperaturePoint {
        :>> mnemonic = "THM_ZONE_T_99"; :>> pointId = 5099; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT100 : TemperaturePoint {
        :>> mnemonic = "THM_ZONE_T_100"; :>> pointId = 5100; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT101 : TemperaturePoint {
        :>> mnemonic = "THM_ZONE_T_101"; :>> pointId = 5101; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT102 : TemperaturePoint {
        :>> mnemonic = "THM_ZONE_T_102"; :>> pointId = 5102; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT103 : TemperaturePoint {
        :>> mnemonic = "THM_ZONE_T_103"; :>> pointId = 5103; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT104 : TemperaturePoint {
        :>> mnemonic = "THM_ZONE_T_104"; :>> pointId = 5104; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT105 : TemperaturePoint {
        :>> mnemonic = "THM_ZONE_T_105"; :>> pointId = 5105; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT106 : TemperaturePoint {
        :>> mnemonic = "THM_ZONE_T_106"; :>> pointId = 5106; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT107 : TemperaturePoint {
        :>> mnemonic = "THM_ZONE_T_107"; :>> pointId = 5107; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT108 : TemperaturePoint {
        :>> mnemonic = "THM_ZONE_T_108"; :>> pointId = 5108; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT109 : TemperaturePoint {
        :>> mnemonic = "THM_ZONE_T_109"; :>> pointId = 5109; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT110 : TemperaturePoint {
        :>> mnemonic = "THM_ZONE_T_110"; :>> pointId = 5110; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT111 : TemperaturePoint {
        :>> mnemonic = "THM_ZONE_T_111"; :>> pointId = 5111; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT112 : TemperaturePoint {
        :>> mnemonic = "THM_ZONE_T_112"; :>> pointId = 5112; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT113 : TemperaturePoint {
        :>> mnemonic = "THM_ZONE_T_113"; :>> pointId = 5113; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT114 : TemperaturePoint {
        :>> mnemonic = "THM_ZONE_T_114"; :>> pointId = 5114; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT115 : TemperaturePoint {
        :>> mnemonic = "THM_ZONE_T_115"; :>> pointId = 5115; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT116 : TemperaturePoint {
        :>> mnemonic = "THM_ZONE_T_116"; :>> pointId = 5116; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT117 : TemperaturePoint {
        :>> mnemonic = "THM_ZONE_T_117"; :>> pointId = 5117; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT118 : TemperaturePoint {
        :>> mnemonic = "THM_ZONE_T_118"; :>> pointId = 5118; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT119 : TemperaturePoint {
        :>> mnemonic = "THM_ZONE_T_119"; :>> pointId = 5119; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT120 : TemperaturePoint {
        :>> mnemonic = "THM_ZONE_T_120"; :>> pointId = 5120; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT121 : TemperaturePoint {
        :>> mnemonic = "THM_ZONE_T_121"; :>> pointId = 5121; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT122 : TemperaturePoint {
        :>> mnemonic = "THM_ZONE_T_122"; :>> pointId = 5122; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT123 : TemperaturePoint {
        :>> mnemonic = "THM_ZONE_T_123"; :>> pointId = 5123; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT124 : TemperaturePoint {
        :>> mnemonic = "THM_ZONE_T_124"; :>> pointId = 5124; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT125 : TemperaturePoint {
        :>> mnemonic = "THM_ZONE_T_125"; :>> pointId = 5125; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT126 : TemperaturePoint {
        :>> mnemonic = "THM_ZONE_T_126"; :>> pointId = 5126; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT127 : TemperaturePoint {
        :>> mnemonic = "THM_ZONE_T_127"; :>> pointId = 5127; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT128 : TemperaturePoint {
        :>> mnemonic = "THM_ZONE_T_128"; :>> pointId = 5128; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT129 : TemperaturePoint {
        :>> mnemonic = "THM_ZONE_T_129"; :>> pointId = 5129; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT130 : TemperaturePoint {
        :>> mnemonic = "THM_ZONE_T_130"; :>> pointId = 5130; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT131 : TemperaturePoint {
        :>> mnemonic = "THM_ZONE_T_131"; :>> pointId = 5131; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT132 : TemperaturePoint {
        :>> mnemonic = "THM_ZONE_T_132"; :>> pointId = 5132; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT133 : TemperaturePoint {
        :>> mnemonic = "THM_ZONE_T_133"; :>> pointId = 5133; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT134 : TemperaturePoint {
        :>> mnemonic = "THM_ZONE_T_134"; :>> pointId = 5134; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT135 : TemperaturePoint {
        :>> mnemonic = "THM_ZONE_T_135"; :>> pointId = 5135; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT136 : TemperaturePoint {
        :>> mnemonic = "THM_ZONE_T_136"; :>> pointId = 5136; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT137 : TemperaturePoint {
        :>> mnemonic = "THM_ZONE_T_137"; :>> pointId = 5137; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT138 : TemperaturePoint {
        :>> mnemonic = "THM_ZONE_T_138"; :>> pointId = 5138; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT139 : TemperaturePoint {
        :>> mnemonic = "THM_ZONE_T_139"; :>> pointId = 5139; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT140 : TemperaturePoint {
        :>> mnemonic = "THM_ZONE_T_140"; :>> pointId = 5140; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT141 : TemperaturePoint {
        :>> mnemonic = "THM_ZONE_T_141"; :>> pointId = 5141; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT142 : TemperaturePoint {
        :>> mnemonic = "THM_ZONE_T_142"; :>> pointId = 5142; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT143 : TemperaturePoint {
        :>> mnemonic = "THM_ZONE_T_143"; :>> pointId = 5143; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT144 : TemperaturePoint {
        :>> mnemonic = "THM_ZONE_T_144"; :>> pointId = 5144; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT145 : TemperaturePoint {
        :>> mnemonic = "THM_ZONE_T_145"; :>> pointId = 5145; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT146 : TemperaturePoint {
        :>> mnemonic = "THM_ZONE_T_146"; :>> pointId = 5146; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT147 : TemperaturePoint {
        :>> mnemonic = "THM_ZONE_T_147"; :>> pointId = 5147; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT148 : TemperaturePoint {
        :>> mnemonic = "THM_ZONE_T_148"; :>> pointId = 5148; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT149 : TemperaturePoint {
        :>> mnemonic = "THM_ZONE_T_149"; :>> pointId = 5149; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT150 : TemperaturePoint {
        :>> mnemonic = "THM_ZONE_T_150"; :>> pointId = 5150; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT151 : TemperaturePoint {
        :>> mnemonic = "THM_ZONE_T_151"; :>> pointId = 5151; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT152 : TemperaturePoint {
        :>> mnemonic = "THM_ZONE_T_152"; :>> pointId = 5152; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT153 : TemperaturePoint {
        :>> mnemonic = "THM_ZONE_T_153"; :>> pointId = 5153; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT154 : TemperaturePoint {
        :>> mnemonic = "THM_ZONE_T_154"; :>> pointId = 5154; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT155 : TemperaturePoint {
        :>> mnemonic = "THM_ZONE_T_155"; :>> pointId = 5155; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT156 : TemperaturePoint {
        :>> mnemonic = "THM_ZONE_T_156"; :>> pointId = 5156; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT157 : TemperaturePoint {
        :>> mnemonic = "THM_ZONE_T_157"; :>> pointId = 5157; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT158 : TemperaturePoint {
        :>> mnemonic = "THM_ZONE_T_158"; :>> pointId = 5158; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT159 : TemperaturePoint {
        :>> mnemonic = "THM_ZONE_T_159"; :>> pointId = 5159; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT160 : TemperaturePoint {
        :>> mnemonic = "THM_ZONE_T_160"; :>> pointId = 5160; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT161 : TemperaturePoint {
        :>> mnemonic = "THM_ZONE_T_161"; :>> pointId = 5161; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT162 : TemperaturePoint {
        :>> mnemonic = "THM_ZONE_T_162"; :>> pointId = 5162; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT163 : TemperaturePoint {
        :>> mnemonic = "THM_ZONE_T_163"; :>> pointId = 5163; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT164 : TemperaturePoint {
        :>> mnemonic = "THM_ZONE_T_164"; :>> pointId = 5164; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT165 : TemperaturePoint {
        :>> mnemonic = "THM_ZONE_T_165"; :>> pointId = 5165; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT166 : TemperaturePoint {
        :>> mnemonic = "THM_ZONE_T_166"; :>> pointId = 5166; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT167 : TemperaturePoint {
        :>> mnemonic = "THM_ZONE_T_167"; :>> pointId = 5167; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT168 : TemperaturePoint {
        :>> mnemonic = "THM_ZONE_T_168"; :>> pointId = 5168; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT169 : TemperaturePoint {
        :>> mnemonic = "THM_ZONE_T_169"; :>> pointId = 5169; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT170 : TemperaturePoint {
        :>> mnemonic = "THM_ZONE_T_170"; :>> pointId = 5170; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT171 : TemperaturePoint {
        :>> mnemonic = "THM_ZONE_T_171"; :>> pointId = 5171; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT172 : TemperaturePoint {
        :>> mnemonic = "THM_ZONE_T_172"; :>> pointId = 5172; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT173 : TemperaturePoint {
        :>> mnemonic = "THM_ZONE_T_173"; :>> pointId = 5173; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT174 : TemperaturePoint {
        :>> mnemonic = "THM_ZONE_T_174"; :>> pointId = 5174; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT175 : TemperaturePoint {
        :>> mnemonic = "THM_ZONE_T_175"; :>> pointId = 5175; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT176 : TemperaturePoint {
        :>> mnemonic = "THM_ZONE_T_176"; :>> pointId = 5176; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT177 : TemperaturePoint {
        :>> mnemonic = "THM_ZONE_T_177"; :>> pointId = 5177; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT178 : TemperaturePoint {
        :>> mnemonic = "THM_ZONE_T_178"; :>> pointId = 5178; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT179 : TemperaturePoint {
        :>> mnemonic = "THM_ZONE_T_179"; :>> pointId = 5179; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT180 : TemperaturePoint {
        :>> mnemonic = "THM_ZONE_T_180"; :>> pointId = 5180; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT181 : TemperaturePoint {
        :>> mnemonic = "THM_ZONE_T_181"; :>> pointId = 5181; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT182 : TemperaturePoint {
        :>> mnemonic = "THM_ZONE_T_182"; :>> pointId = 5182; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT183 : TemperaturePoint {
        :>> mnemonic = "THM_ZONE_T_183"; :>> pointId = 5183; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT184 : TemperaturePoint {
        :>> mnemonic = "THM_ZONE_T_184"; :>> pointId = 5184; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT185 : TemperaturePoint {
        :>> mnemonic = "THM_ZONE_T_185"; :>> pointId = 5185; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT186 : TemperaturePoint {
        :>> mnemonic = "THM_ZONE_T_186"; :>> pointId = 5186; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT187 : TemperaturePoint {
        :>> mnemonic = "THM_ZONE_T_187"; :>> pointId = 5187; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT188 : TemperaturePoint {
        :>> mnemonic = "THM_ZONE_T_188"; :>> pointId = 5188; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT189 : TemperaturePoint {
        :>> mnemonic = "THM_ZONE_T_189"; :>> pointId = 5189; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT190 : TemperaturePoint {
        :>> mnemonic = "THM_ZONE_T_190"; :>> pointId = 5190; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT191 : TemperaturePoint {
        :>> mnemonic = "THM_ZONE_T_191"; :>> pointId = 5191; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmZoneT192 : TemperaturePoint {
        :>> mnemonic = "THM_ZONE_T_192"; :>> pointId = 5192; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmHtrState01 : StatusPoint {
        :>> mnemonic = "THM_HTR_STATE_01"; :>> pointId = 5193; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState02 : StatusPoint {
        :>> mnemonic = "THM_HTR_STATE_02"; :>> pointId = 5194; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState03 : StatusPoint {
        :>> mnemonic = "THM_HTR_STATE_03"; :>> pointId = 5195; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState04 : StatusPoint {
        :>> mnemonic = "THM_HTR_STATE_04"; :>> pointId = 5196; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState05 : StatusPoint {
        :>> mnemonic = "THM_HTR_STATE_05"; :>> pointId = 5197; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState06 : StatusPoint {
        :>> mnemonic = "THM_HTR_STATE_06"; :>> pointId = 5198; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState07 : StatusPoint {
        :>> mnemonic = "THM_HTR_STATE_07"; :>> pointId = 5199; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState08 : StatusPoint {
        :>> mnemonic = "THM_HTR_STATE_08"; :>> pointId = 5200; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState09 : StatusPoint {
        :>> mnemonic = "THM_HTR_STATE_09"; :>> pointId = 5201; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState10 : StatusPoint {
        :>> mnemonic = "THM_HTR_STATE_10"; :>> pointId = 5202; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState11 : StatusPoint {
        :>> mnemonic = "THM_HTR_STATE_11"; :>> pointId = 5203; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState12 : StatusPoint {
        :>> mnemonic = "THM_HTR_STATE_12"; :>> pointId = 5204; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState13 : StatusPoint {
        :>> mnemonic = "THM_HTR_STATE_13"; :>> pointId = 5205; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState14 : StatusPoint {
        :>> mnemonic = "THM_HTR_STATE_14"; :>> pointId = 5206; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState15 : StatusPoint {
        :>> mnemonic = "THM_HTR_STATE_15"; :>> pointId = 5207; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrState16 : StatusPoint {
        :>> mnemonic = "THM_HTR_STATE_16"; :>> pointId = 5208; :>> source = ApplicationName::thermalControl; :>> apidClass = ApidClass::housekeeping;
        :>> kind = TelemetryKind::housekeeping; :>> rate = 1.0 [Hz];
        :>> redLow = 0; :>> yellowLow = 0; :>> yellowHigh = 1; :>> redHigh = 1;
    }
    item thmHtrDuty01 : FractionPoint {
        :>> mnemonic = "THM_HTR_DUTY_01"; :>> pointId = 5209; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty02 : FractionPoint {
        :>> mnemonic = "THM_HTR_DUTY_02"; :>> pointId = 5210; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty03 : FractionPoint {
        :>> mnemonic = "THM_HTR_DUTY_03"; :>> pointId = 5211; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty04 : FractionPoint {
        :>> mnemonic = "THM_HTR_DUTY_04"; :>> pointId = 5212; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty05 : FractionPoint {
        :>> mnemonic = "THM_HTR_DUTY_05"; :>> pointId = 5213; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty06 : FractionPoint {
        :>> mnemonic = "THM_HTR_DUTY_06"; :>> pointId = 5214; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty07 : FractionPoint {
        :>> mnemonic = "THM_HTR_DUTY_07"; :>> pointId = 5215; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty08 : FractionPoint {
        :>> mnemonic = "THM_HTR_DUTY_08"; :>> pointId = 5216; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty09 : FractionPoint {
        :>> mnemonic = "THM_HTR_DUTY_09"; :>> pointId = 5217; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty10 : FractionPoint {
        :>> mnemonic = "THM_HTR_DUTY_10"; :>> pointId = 5218; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty11 : FractionPoint {
        :>> mnemonic = "THM_HTR_DUTY_11"; :>> pointId = 5219; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty12 : FractionPoint {
        :>> mnemonic = "THM_HTR_DUTY_12"; :>> pointId = 5220; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty13 : FractionPoint {
        :>> mnemonic = "THM_HTR_DUTY_13"; :>> pointId = 5221; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty14 : FractionPoint {
        :>> mnemonic = "THM_HTR_DUTY_14"; :>> pointId = 5222; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty15 : FractionPoint {
        :>> mnemonic = "THM_HTR_DUTY_15"; :>> pointId = 5223; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrDuty16 : FractionPoint {
        :>> mnemonic = "THM_HTR_DUTY_16"; :>> pointId = 5224; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHtrI01 : CurrentPoint {
        :>> mnemonic = "THM_HTR_I_01"; :>> pointId = 5225; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI02 : CurrentPoint {
        :>> mnemonic = "THM_HTR_I_02"; :>> pointId = 5226; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI03 : CurrentPoint {
        :>> mnemonic = "THM_HTR_I_03"; :>> pointId = 5227; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI04 : CurrentPoint {
        :>> mnemonic = "THM_HTR_I_04"; :>> pointId = 5228; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI05 : CurrentPoint {
        :>> mnemonic = "THM_HTR_I_05"; :>> pointId = 5229; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI06 : CurrentPoint {
        :>> mnemonic = "THM_HTR_I_06"; :>> pointId = 5230; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI07 : CurrentPoint {
        :>> mnemonic = "THM_HTR_I_07"; :>> pointId = 5231; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI08 : CurrentPoint {
        :>> mnemonic = "THM_HTR_I_08"; :>> pointId = 5232; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI09 : CurrentPoint {
        :>> mnemonic = "THM_HTR_I_09"; :>> pointId = 5233; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI10 : CurrentPoint {
        :>> mnemonic = "THM_HTR_I_10"; :>> pointId = 5234; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI11 : CurrentPoint {
        :>> mnemonic = "THM_HTR_I_11"; :>> pointId = 5235; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI12 : CurrentPoint {
        :>> mnemonic = "THM_HTR_I_12"; :>> pointId = 5236; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI13 : CurrentPoint {
        :>> mnemonic = "THM_HTR_I_13"; :>> pointId = 5237; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI14 : CurrentPoint {
        :>> mnemonic = "THM_HTR_I_14"; :>> pointId = 5238; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI15 : CurrentPoint {
        :>> mnemonic = "THM_HTR_I_15"; :>> pointId = 5239; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmHtrI16 : CurrentPoint {
        :>> mnemonic = "THM_HTR_I_16"; :>> pointId = 5240; :>> source = ApplicationName::thermalControl; :>> apidClass = ApidClass::housekeeping;
        :>> kind = TelemetryKind::engineering; :>> rate = 0.1 [Hz];
        :>> redLow = 0.0 [A]; :>> yellowLow = 0.0 [A]; :>> yellowHigh = 8.0 [A]; :>> redHigh = 10.0 [A];
    }
    item thmSetpoint01 : TemperaturePoint {
        :>> mnemonic = "THM_SETPOINT_01"; :>> pointId = 5241; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint02 : TemperaturePoint {
        :>> mnemonic = "THM_SETPOINT_02"; :>> pointId = 5242; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint03 : TemperaturePoint {
        :>> mnemonic = "THM_SETPOINT_03"; :>> pointId = 5243; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint04 : TemperaturePoint {
        :>> mnemonic = "THM_SETPOINT_04"; :>> pointId = 5244; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint05 : TemperaturePoint {
        :>> mnemonic = "THM_SETPOINT_05"; :>> pointId = 5245; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint06 : TemperaturePoint {
        :>> mnemonic = "THM_SETPOINT_06"; :>> pointId = 5246; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint07 : TemperaturePoint {
        :>> mnemonic = "THM_SETPOINT_07"; :>> pointId = 5247; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint08 : TemperaturePoint {
        :>> mnemonic = "THM_SETPOINT_08"; :>> pointId = 5248; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint09 : TemperaturePoint {
        :>> mnemonic = "THM_SETPOINT_09"; :>> pointId = 5249; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint10 : TemperaturePoint {
        :>> mnemonic = "THM_SETPOINT_10"; :>> pointId = 5250; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint11 : TemperaturePoint {
        :>> mnemonic = "THM_SETPOINT_11"; :>> pointId = 5251; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint12 : TemperaturePoint {
        :>> mnemonic = "THM_SETPOINT_12"; :>> pointId = 5252; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint13 : TemperaturePoint {
        :>> mnemonic = "THM_SETPOINT_13"; :>> pointId = 5253; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint14 : TemperaturePoint {
        :>> mnemonic = "THM_SETPOINT_14"; :>> pointId = 5254; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint15 : TemperaturePoint {
        :>> mnemonic = "THM_SETPOINT_15"; :>> pointId = 5255; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmSetpoint16 : TemperaturePoint {
        :>> mnemonic = "THM_SETPOINT_16"; :>> pointId = 5256; :>> source = ApplicationName::thermalControl; :>> apidClass = ApidClass::housekeeping;
        :>> kind = TelemetryKind::engineering; :>> rate = 0.01 [Hz];
        :>> redLow = 233.0 [K]; :>> yellowLow = 253.0 [K]; :>> yellowHigh = 313.0 [K]; :>> redHigh = 333.0 [K];
    }
    item thmLouverPos01 : FractionPoint {
        :>> mnemonic = "THM_LOUVER_POS_01"; :>> pointId = 5257; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmLouverPos02 : FractionPoint {
        :>> mnemonic = "THM_LOUVER_POS_02"; :>> pointId = 5258; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmLouverPos03 : FractionPoint {
        :>> mnemonic = "THM_LOUVER_POS_03"; :>> pointId = 5259; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmLouverPos04 : FractionPoint {
        :>> mnemonic = "THM_LOUVER_POS_04"; :>> pointId = 5260; :>> source = ApplicationName::thermalControl; :>> apidClass = ApidClass::housekeeping;
        :>> kind = TelemetryKind::engineering; :>> rate = 0.1 [Hz];
        :>> redLow = 0.0; :>> yellowLow = 0.1; :>> yellowHigh = 0.9; :>> redHigh = 1.0;
    }
    item thmHeatPipeT01 : TemperaturePoint {
        :>> mnemonic = "THM_HEAT_PIPE_T_01"; :>> pointId = 5261; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmHeatPipeT02 : TemperaturePoint {
        :>> mnemonic = "THM_HEAT_PIPE_T_02"; :>> pointId = 5262; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmHeatPipeT03 : TemperaturePoint {
        :>> mnemonic = "THM_HEAT_PIPE_T_03"; :>> pointId = 5263; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmHeatPipeT04 : TemperaturePoint {
        :>> mnemonic = "THM_HEAT_PIPE_T_04"; :>> pointId = 5264; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmHeatPipeT05 : TemperaturePoint {
        :>> mnemonic = "THM_HEAT_PIPE_T_05"; :>> pointId = 5265; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmHeatPipeT06 : TemperaturePoint {
        :>> mnemonic = "THM_HEAT_PIPE_T_06"; :>> pointId = 5266; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmHeatPipeT07 : TemperaturePoint {
        :>> mnemonic = "THM_HEAT_PIPE_T_07"; :>> pointId = 5267; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmHeatPipeT08 : TemperaturePoint {
        :>> mnemonic = "THM_HEAT_PIPE_T_08"; :>> pointId = 5268; :>> source = ApplicationName::thermalControl; :>> apidClass = ApidClass::housekeeping;
        :>> kind = TelemetryKind::engineering; :>> rate = 0.1 [Hz];
        :>> redLow = 233.0 [K]; :>> yellowLow = 253.0 [K]; :>> yellowHigh = 313.0 [K]; :>> redHigh = 333.0 [K];
    }
    item thmRadiatorT01 : TemperaturePoint {
        :>> mnemonic = "THM_RADIATOR_T_01"; :>> pointId = 5269; :>> source = ApplicationName::thermalControl; :>> apidClass = ApidClass::housekeeping;
        :>> kind = TelemetryKind::housekeeping; :>> rate = 0.1 [Hz];
        :>> redLow = 173.0 [K]; :>> yellowLow = 193.0 [K]; :>> yellowHigh = 323.0 [K]; :>> redHigh = 343.0 [K];
    }
    item thmRadiatorT02 : TemperaturePoint {
        :>> mnemonic = "THM_RADIATOR_T_02"; :>> pointId = 5270; :>> source = ApplicationName::thermalControl; :>> apidClass = ApidClass::housekeeping;
        :>> kind = TelemetryKind::housekeeping; :>> rate = 0.1 [Hz];
        :>> redLow = 173.0 [K]; :>> yellowLow = 193.0 [K]; :>> yellowHigh = 323.0 [K]; :>> redHigh = 343.0 [K];
    }
    item thmRadiatorT03 : TemperaturePoint {
        :>> mnemonic = "THM_RADIATOR_T_03"; :>> pointId = 5271; :>> source = ApplicationName::thermalControl; :>> apidClass = ApidClass::housekeeping;
        :>> kind = TelemetryKind::housekeeping; :>> rate = 0.1 [Hz];
        :>> redLow = 173.0 [K]; :>> yellowLow = 193.0 [K]; :>> yellowHigh = 323.0 [K]; :>> redHigh = 343.0 [K];
    }
    item thmRadiatorT04 : TemperaturePoint {
        :>> mnemonic = "THM_RADIATOR_T_04"; :>> pointId = 5272; :>> source = ApplicationName::thermalControl; :>> apidClass = ApidClass::housekeeping;
        :>> kind = TelemetryKind::housekeeping; :>> rate = 0.1 [Hz];
        :>> redLow = 173.0 [K]; :>> yellowLow = 193.0 [K]; :>> yellowHigh = 323.0 [K]; :>> redHigh = 343.0 [K];
    }
    item thmHtrPowerTotal : PowerPoint {
        :>> mnemonic = "THM_HTR_POWER_TOTAL"; :>> pointId = 5273; :>> source = ApplicationName::thermalControl; :>> apidClass = ApidClass::housekeeping;
        :>> kind = TelemetryKind::housekeeping; :>> rate = 1.0 [Hz];
        :>> redLow = 0.0 [W]; :>> yellowLow = 0.0 [W]; :>> yellowHigh = 800.0 [W]; :>> redHigh = 900.0 [W];
    }
    item thmControlMode : StatusPoint {
        :>> mnemonic = "THM_CONTROL_MODE"; :>> pointId = 5274; :>> source = ApplicationName::thermalControl; :>> apidClass = ApidClass::housekeeping;
        :>> kind = TelemetryKind::housekeeping; :>> rate = 1.0 [Hz];
        :>> redLow = 0; :>> yellowLow = 0; :>> yellowHigh = 2; :>> redHigh = 2;
    }
    item comTxPower01 : PowerPoint {
        :>> mnemonic = "COM_TX_POWER_01"; :>> pointId = 6001; :>> source = ApplicationName::telecom; :>> apidClass = ApidClass::relay;
        :>> kind = TelemetryKind::housekeeping; :>> rate = 1.0 [Hz];
        :>> redLow = 0.0 [W]; :>> yellowLow = 0.0 [W]; :>> yellowHigh = 100.0 [W]; :>> redHigh = 110.0 [W];
    }
    item comTxPower02 : PowerPoint {
        :>> mnemonic = "COM_TX_POWER_02"; :>> pointId = 6002; :>> source = ApplicationName::telecom; :>> apidClass = ApidClass::relay;
        :>> kind = TelemetryKind::housekeeping; :>> rate = 1.0 [Hz];
        :>> redLow = 0.0 [W]; :>> yellowLow = 0.0 [W]; :>> yellowHigh = 100.0 [W]; :>> redHigh = 110.0 [W];
    }
    item comRxAgc01 : FractionPoint {
        :>> mnemonic = "COM_RX_AGC_01"; :>> pointId = 6003; :>> source = ApplicationName::telecom; :>> apidClass = ApidClass::relay;
        :>> kind = TelemetryKind::housekeeping; :>> rate = 1.0 [Hz];
        :>> redLow = 0.0; :>> yellowLow = 0.1; :>> yellowHigh = 0.9; :>> redHigh = 1.0;
    }
    item comRxAgc02 : FractionPoint {
        :>> mnemonic = "COM_RX_AGC_02"; :>> pointId = 6004; :>> source = ApplicationName::telecom; :>> apidClass = ApidClass::relay;
        :>> kind = TelemetryKind::housekeeping; :>> rate = 1.0 [Hz];
        :>> redLow = 0.0; :>> yellowLow = 0.1; :>> yellowHigh = 0.9; :>> redHigh = 1.0;
    }
    item comRxLock01 : StatusPoint {
        :>> mnemonic = "COM_RX_LOCK_01"; :>> pointId = 6005; :>> source = ApplicationName::telecom; :>> apidClass = ApidClass::relay;
        :>> kind = TelemetryKind::housekeeping; :>> rate = 1.0 [Hz];
        :>> redLow = 0; :>> yellowLow = 0; :>> yellowHigh = 1; :>> redHigh = 1;
    }
    item comRxLock02 : StatusPoint {
        :>> mnemonic = "COM_RX_LOCK_02"; :>> pointId = 6006; :>> source = ApplicationName::telecom; :>> apidClass = ApidClass::relay;
        :>> kind = TelemetryKind::housekeeping; :>> rate = 1.0 [Hz];
        :>> redLow = 0; :>> yellowLow = 0; :>> yellowHigh = 1; :>> redHigh = 1;
    }
    item comCarrierLock : StatusPoint {
        :>> mnemonic = "COM_CARRIER_LOCK"; :>> pointId = 6007; :>> source = ApplicationName::telecom; :>> apidClass = ApidClass::relay;
        :>> kind = TelemetryKind::housekeeping; :>> rate = 1.0 [Hz];
        :>> redLow = 0; :>> yellowLow = 0; :>> yellowHigh = 1; :>> redHigh = 1;
    }
    item comSymbolRate : CountPoint {
        :>> mnemonic = "COM_SYMBOL_RATE"; :>> pointId = 6008; :>> source = ApplicationName::telecom; :>> apidClass = ApidClass::relay;
        :>> kind = TelemetryKind::housekeeping; :>> rate = 0.1 [Hz];
        :>> redLow = 0; :>> yellowLow = 0; :>> yellowHigh = 61035 * 65536 + 10240; :>> redHigh = 65535 * 65536 + 65535;
    }
    item comUplinkRate : CountPoint {
        :>> mnemonic = "COM_UPLINK_RATE"; :>> pointId = 6009; :>> source = ApplicationName::telecom; :>> apidClass = ApidClass::relay;
        :>> kind = TelemetryKind::engineering; :>> rate = 0.1 [Hz];
        :>> redLow = 0; :>> yellowLow = 0; :>> yellowHigh = 61035 * 65536 + 10240; :>> redHigh = 65535 * 65536 + 65535;
    }
    item comFrameCount : CountPoint {
        :>> mnemonic = "COM_FRAME_COUNT"; :>> pointId = 6010; :>> source = ApplicationName::telecom; :>> apidClass = ApidClass::relay;
        :>> kind = TelemetryKind::engineering; :>> rate = 1.0 [Hz];
        :>> redLow = 0; :>> yellowLow = 0; :>> yellowHigh = 61035 * 65536 + 10240; :>> redHigh = 65535 * 65536 + 65535;
    }
    item comFrameErrors : CountPoint {
        :>> mnemonic = "COM_FRAME_ERRORS"; :>> pointId = 6011; :>> source = ApplicationName::telecom; :>> apidClass = ApidClass::relay;
        :>> kind = TelemetryKind::engineering; :>> rate = 1.0 [Hz];
        :>> redLow = 0; :>> yellowLow = 0; :>> yellowHigh = 100; :>> redHigh = 1000;
    }
    item comSspaT01 : TemperaturePoint {
        :>> mnemonic = "COM_SSPA_T_01"; :>> pointId = 6012; :>> source = ApplicationName::telecom; :>> apidClass = ApidClass::relay;
        :>> kind = TelemetryKind::housekeeping; :>> rate = 0.1 [Hz];
        :>> redLow = 233.0 [K]; :>> yellowLow = 253.0 [K]; :>> yellowHigh = 343.0 [K]; :>> redHigh = 353.0 [K];
    }
    item comSspaT02 : TemperaturePoint {
        :>> mnemonic = "COM_SSPA_T_02"; :>> pointId = 6013; :>> source = ApplicationName::telecom; :>> apidClass = ApidClass::relay;
        :>> kind = TelemetryKind::housekeeping; :>> rate = 0.1 [Hz];
        :>> redLow = 233.0 [K]; :>> yellowLow = 253.0 [K]; :>> yellowHigh = 343.0 [K]; :>> redHigh = 353.0 [K];
    }
    item comSspaI01 : CurrentPoint {
        :>> mnemonic = "COM_SSPA_I_01"; :>> pointId = 6014; :>> source = ApplicationName::telecom; :>> apidClass = ApidClass::relay;
        :>> kind = TelemetryKind::engineering; :>> rate = 1.0 [Hz];
        :>> redLow = 0.0 [A]; :>> yellowLow = 0.0 [A]; :>> yellowHigh = 8.0 [A]; :>> redHigh = 10.0 [A];
    }
    item comSspaI02 : CurrentPoint {
        :>> mnemonic = "COM_SSPA_I_02"; :>> pointId = 6015; :>> source = ApplicationName::telecom; :>> apidClass = ApidClass::relay;
        :>> kind = TelemetryKind::engineering; :>> rate = 1.0 [Hz];
        :>> redLow = 0.0 [A]; :>> yellowLow = 0.0 [A]; :>> yellowHigh = 8.0 [A]; :>> redHigh = 10.0 [A];
    }
    item comHgaAz : AnglePoint {
        :>> mnemonic = "COM_HGA_AZ"; :>> pointId = 6016; :>> source = ApplicationName::telecom; :>> apidClass = ApidClass::relay;
        :>> kind = TelemetryKind::housekeeping; :>> rate = 1.0 [Hz];
        :>> redLow = -1.6 [rad]; :>> yellowLow = -1.5708 [rad]; :>> yellowHigh = 1.5708 [rad]; :>> redHigh = 1.6 [rad];
    }
    item comHgaEl : AnglePoint {
        :>> mnemonic = "COM_HGA_EL"; :>> pointId = 6017; :>> source = ApplicationName::telecom; :>> apidClass = ApidClass::relay;
        :>> kind = TelemetryKind::housekeeping; :>> rate = 1.0 [Hz];
        :>> redLow = -0.8 [rad]; :>> yellowLow = -0.7854 [rad]; :>> yellowHigh = 0.7854 [rad]; :>> redHigh = 0.8 [rad];
    }
    item comAntennaSel : StatusPoint {
        :>> mnemonic = "COM_ANTENNA_SEL"; :>> pointId = 6018; :>> source = ApplicationName::telecom; :>> apidClass = ApidClass::relay;
        :>> kind = TelemetryKind::housekeeping; :>> rate = 1.0 [Hz];
        :>> redLow = 0; :>> yellowLow = 0; :>> yellowHigh = 2; :>> redHigh = 2;
    }
    item comRangingState : StatusPoint {
        :>> mnemonic = "COM_RANGING_STATE"; :>> pointId = 6019; :>> source = ApplicationName::telecom; :>> apidClass = ApidClass::relay;
        :>> kind = TelemetryKind::housekeeping; :>> rate = 1.0 [Hz];
        :>> redLow = 0; :>> yellowLow = 0; :>> yellowHigh = 1; :>> redHigh = 1;
    }
    item comDoppler : FractionPoint {
        :>> mnemonic = "COM_DOPPLER"; :>> pointId = 6020; :>> source = ApplicationName::telecom; :>> apidClass = ApidClass::relay;
        :>> kind = TelemetryKind::engineering; :>> rate = 1.0 [Hz];
        :>> redLow = 0.0; :>> yellowLow = 0.1; :>> yellowHigh = 0.9; :>> redHigh = 1.0;
    }
    item comTwoWayRange : LengthPoint {
        :>> mnemonic = "COM_TWO_WAY_RANGE"; :>> pointId = 6021; :>> source = ApplicationName::telecom; :>> apidClass = ApidClass::relay;
        :>> kind = TelemetryKind::engineering; :>> rate = 0.1 [Hz];
        :>> redLow = 0.0 [m]; :>> yellowLow = 10.0 [m]; :>> yellowHigh = 100000000.0 [m]; :>> redHigh = 1000000000.0 [m];
    }
    item comLinkMargin : FractionPoint {
        :>> mnemonic = "COM_LINK_MARGIN"; :>> pointId = 6022; :>> source = ApplicationName::telecom; :>> apidClass = ApidClass::relay;
        :>> kind = TelemetryKind::housekeeping; :>> rate = 1.0 [Hz];
        :>> redLow = 0.0; :>> yellowLow = 3.0; :>> yellowHigh = 30.0; :>> redHigh = 40.0;
    }
    item comPassRemaining : DurationPoint {
        :>> mnemonic = "COM_PASS_REMAINING"; :>> pointId = 6023; :>> source = ApplicationName::telecom; :>> apidClass = ApidClass::relay;
        :>> kind = TelemetryKind::engineering; :>> rate = 1.0 [Hz];
        :>> redLow = 0.0 [s]; :>> yellowLow = 0.0 [s]; :>> yellowHigh = 10000000.0 [s]; :>> redHigh = 100000000.0 [s];
    }
    item comExciterT01 : TemperaturePoint {
        :>> mnemonic = "COM_EXCITER_T_01"; :>> pointId = 6024; :>> source = ApplicationName::telecom; :>> apidClass = ApidClass::relay;
        :>> kind = TelemetryKind::engineering; :>> rate = 0.1 [Hz];
        :>> redLow = 233.0 [K]; :>> yellowLow = 253.0 [K]; :>> yellowHigh = 313.0 [K]; :>> redHigh = 333.0 [K];
    }
    item comExciterT02 : TemperaturePoint {
        :>> mnemonic = "COM_EXCITER_T_02"; :>> pointId = 6025; :>> source = ApplicationName::telecom; :>> apidClass = ApidClass::relay;
        :>> kind = TelemetryKind::engineering; :>> rate = 0.1 [Hz];
        :>> redLow = 233.0 [K]; :>> yellowLow = 253.0 [K]; :>> yellowHigh = 313.0 [K]; :>> redHigh = 333.0 [K];
    }
    item comXpdrState01 : StatusPoint {
        :>> mnemonic = "COM_XPDR_STATE_01"; :>> pointId = 6026; :>> source = ApplicationName::telecom; :>> apidClass = ApidClass::relay;
        :>> kind = TelemetryKind::housekeeping; :>> rate = 1.0 [Hz];
        :>> redLow = 0; :>> yellowLow = 0; :>> yellowHigh = 254; :>> redHigh = 255;
    }
    item comXpdrState02 : StatusPoint {
        :>> mnemonic = "COM_XPDR_STATE_02"; :>> pointId = 6027; :>> source = ApplicationName::telecom; :>> apidClass = ApidClass::relay;
        :>> kind = TelemetryKind::housekeeping; :>> rate = 1.0 [Hz];
        :>> redLow = 0; :>> yellowLow = 0; :>> yellowHigh = 254; :>> redHigh = 255;
    }
    item comHgaT01 : TemperaturePoint {
        :>> mnemonic = "COM_HGA_T_01"; :>> pointId = 6028; :>> source = ApplicationName::telecom; :>> apidClass = ApidClass::relay;
        :>> kind = TelemetryKind::engineering; :>> rate = 0.1 [Hz];
        :>> redLow = 233.0 [K]; :>> yellowLow = 253.0 [K]; :>> yellowHigh = 313.0 [K]; :>> redHigh = 333.0 [K];
    }
    item comHgaT02 : TemperaturePoint {
        :>> mnemonic = "COM_HGA_T_02"; :>> pointId = 6029; :>> source = ApplicationName::telecom; :>> apidClass = ApidClass::relay;
        :>> kind = TelemetryKind::engineering; :>> rate = 0.1 [Hz];
        :>> redLow = 233.0 [K]; :>> yellowLow = 253.0 [K]; :>> yellowHigh = 313.0 [K]; :>> redHigh = 333.0 [K];
    }
    item comRelayRxLock : StatusPoint {
        :>> mnemonic = "COM_RELAY_RX_LOCK"; :>> pointId = 6030; :>> source = ApplicationName::telecom; :>> apidClass = ApidClass::relay;
        :>> kind = TelemetryKind::housekeeping; :>> rate = 1.0 [Hz];
        :>> redLow = 0; :>> yellowLow = 0; :>> yellowHigh = 1; :>> redHigh = 1;
    }
    item comRelayRate : CountPoint {
        :>> mnemonic = "COM_RELAY_RATE"; :>> pointId = 6031; :>> source = ApplicationName::telecom; :>> apidClass = ApidClass::relay;
        :>> kind = TelemetryKind::engineering; :>> rate = 0.1 [Hz];
        :>> redLow = 0; :>> yellowLow = 0; :>> yellowHigh = 61035 * 65536 + 10240; :>> redHigh = 65535 * 65536 + 65535;
    }
    item comRelayFrameCount : CountPoint {
        :>> mnemonic = "COM_RELAY_FRAME_COUNT"; :>> pointId = 6032; :>> source = ApplicationName::telecom; :>> apidClass = ApidClass::relay;
        :>> kind = TelemetryKind::engineering; :>> rate = 1.0 [Hz];
        :>> redLow = 0; :>> yellowLow = 0; :>> yellowHigh = 61035 * 65536 + 10240; :>> redHigh = 65535 * 65536 + 65535;
    }
    item comRelayLinkMargin : FractionPoint {
        :>> mnemonic = "COM_RELAY_LINK_MARGIN"; :>> pointId = 6033; :>> source = ApplicationName::telecom; :>> apidClass = ApidClass::relay;
        :>> kind = TelemetryKind::housekeeping; :>> rate = 1.0 [Hz];
        :>> redLow = 0.0; :>> yellowLow = 3.0; :>> yellowHigh = 30.0; :>> redHigh = 40.0;
    }
    item comCodingSel : StatusPoint {
        :>> mnemonic = "COM_CODING_SEL"; :>> pointId = 6034; :>> source = ApplicationName::telecom; :>> apidClass = ApidClass::relay;
        :>> kind = TelemetryKind::engineering; :>> rate = 0.1 [Hz];
        :>> redLow = 0; :>> yellowLow = 0; :>> yellowHigh = 254; :>> redHigh = 255;
    }
    item comHgaMotorI01 : CurrentPoint {
        :>> mnemonic = "COM_HGA_MOTOR_I_01"; :>> pointId = 6035; :>> source = ApplicationName::telecom; :>> apidClass = ApidClass::relay;
        :>> kind = TelemetryKind::engineering; :>> rate = 1.0 [Hz];
        :>> redLow = 0.0 [A]; :>> yellowLow = 0.0 [A]; :>> yellowHigh = 8.0 [A]; :>> redHigh = 10.0 [A];
    }
    item comHgaMotorI02 : CurrentPoint {
        :>> mnemonic = "COM_HGA_MOTOR_I_02"; :>> pointId = 6036; :>> source = ApplicationName::telecom; :>> apidClass = ApidClass::relay;
        :>> kind = TelemetryKind::engineering; :>> rate = 1.0 [Hz];
        :>> redLow = 0.0 [A]; :>> yellowLow = 0.0 [A]; :>> yellowHigh = 8.0 [A]; :>> redHigh = 10.0 [A];
    }
    item insInspRange : LengthPoint {
        :>> mnemonic = "INS_INSP_RANGE"; :>> pointId = 7001; :>> source = ApplicationName::inspectorHandling; :>> apidClass = ApidClass::imaging;
        :>> kind = TelemetryKind::housekeeping; :>> rate = 1.0 [Hz];
        :>> redLow = 0.0 [m]; :>> yellowLow = 20.0 [m]; :>> yellowHigh = 5000.0 [m]; :>> redHigh = 10000.0 [m];
    }
    item insInspBearing01 : AnglePoint {
        :>> mnemonic = "INS_INSP_BEARING_01"; :>> pointId = 7002; :>> source = ApplicationName::inspectorHandling; :>> apidClass = ApidClass::imaging;
        :>> kind = TelemetryKind::housekeeping; :>> rate = 1.0 [Hz];
        :>> redLow = -3.1416 [rad]; :>> yellowLow = -3.0 [rad]; :>> yellowHigh = 3.0 [rad]; :>> redHigh = 3.1416 [rad];
    }
    item insInspBearing02 : AnglePoint {
        :>> mnemonic = "INS_INSP_BEARING_02"; :>> pointId = 7003; :>> source = ApplicationName::inspectorHandling; :>> apidClass = ApidClass::imaging;
        :>> kind = TelemetryKind::housekeeping; :>> rate = 1.0 [Hz];
        :>> redLow = -3.1416 [rad]; :>> yellowLow = -3.0 [rad]; :>> yellowHigh = 3.0 [rad]; :>> redHigh = 3.1416 [rad];
    }
    item insInspRangeRate : SpeedPoint {
        :>> mnemonic = "INS_INSP_RANGE_RATE"; :>> pointId = 7004; :>> source = ApplicationName::inspectorHandling; :>> apidClass = ApidClass::imaging;
        :>> kind = TelemetryKind::housekeeping; :>> rate = 1.0 [Hz];
        :>> redLow = -2.0 [m/s]; :>> yellowLow = -1.0 [m/s]; :>> yellowHigh = 1.0 [m/s]; :>> redHigh = 2.0 [m/s];
    }
    item insInspState : StatusPoint {
        :>> mnemonic = "INS_INSP_STATE"; :>> pointId = 7005; :>> source = ApplicationName::inspectorHandling; :>> apidClass = ApidClass::imaging;
        :>> kind = TelemetryKind::housekeeping; :>> rate = 1.0 [Hz];
        :>> redLow = 0; :>> yellowLow = 0; :>> yellowHigh = 254; :>> redHigh = 255;
    }
    item insInspBattV : VoltagePoint {
        :>> mnemonic = "INS_INSP_BATT_V"; :>> pointId = 7006; :>> source = ApplicationName::inspectorHandling; :>> apidClass = ApidClass::imaging;
        :>> kind = TelemetryKind::housekeeping; :>> rate = 0.1 [Hz];
        :>> redLow = 20.0 [V]; :>> yellowLow = 22.0 [V]; :>> yellowHigh = 29.4 [V]; :>> redHigh = 30.0 [V];
    }
    item insInspBattSoc : FractionPoint {
        :>> mnemonic = "INS_INSP_BATT_SOC"; :>> pointId = 7007; :>> source = ApplicationName::inspectorHandling; :>> apidClass = ApidClass::imaging;
        :>> kind = TelemetryKind::housekeeping; :>> rate = 0.1 [Hz];
        :>> redLow = 0.2; :>> yellowLow = 0.3; :>> yellowHigh = 1.0; :>> redHigh = 1.0;
    }
    item insInspT01 : TemperaturePoint {
        :>> mnemonic = "INS_INSP_T_01"; :>> pointId = 7008; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insInspT02 : TemperaturePoint {
        :>> mnemonic = "INS_INSP_T_02"; :>> pointId = 7009; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insInspT03 : TemperaturePoint {
        :>> mnemonic = "INS_INSP_T_03"; :>> pointId = 7010; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insInspT04 : TemperaturePoint {
        :>> mnemonic = "INS_INSP_T_04"; :>> pointId = 7011; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insInspT05 : TemperaturePoint {
        :>> mnemonic = "INS_INSP_T_05"; :>> pointId = 7012; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insInspT06 : TemperaturePoint {
        :>> mnemonic = "INS_INSP_T_06"; :>> pointId = 7013; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insInspT07 : TemperaturePoint {
        :>> mnemonic = "INS_INSP_T_07"; :>> pointId = 7014; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insInspT08 : TemperaturePoint {
        :>> mnemonic = "INS_INSP_T_08"; :>> pointId = 7015; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insImageCount : CountPoint {
        :>> mnemonic = "INS_IMAGE_COUNT"; :>> pointId = 7016; :>> source = ApplicationName::inspectorHandling; :>> apidClass = ApidClass::imaging;
        :>> kind = TelemetryKind::engineering; :>> rate = 0.1 [Hz];
        :>> redLow = 0; :>> yellowLow = 0; :>> yellowHigh = 61035 * 65536 + 10240; :>> redHigh = 65535 * 65536 + 65535;
    }
    item insImageQueue : CountPoint {
        :>> mnemonic = "INS_IMAGE_QUEUE"; :>> pointId = 7017; :>> source = ApplicationName::inspectorHandling; :>> apidClass = ApidClass::imaging;
        :>> kind = TelemetryKind::engineering; :>> rate = 0.1 [Hz];
        :>> redLow = 0; :>> yellowLow = 0; :>> yellowHigh = 200; :>> redHigh = 256;
    }
    item insSegmentsRx : CountPoint {
        :>> mnemonic = "INS_SEGMENTS_RX"; :>> pointId = 7018; :>> source = ApplicationName::inspectorHandling; :>> apidClass = ApidClass::imaging;
        :>> kind = TelemetryKind::engineering; :>> rate = 1.0 [Hz];
        :>> redLow = 0; :>> yellowLow = 0; :>> yellowHigh = 61035 * 65536 + 10240; :>> redHigh = 65535 * 65536 + 65535;
    }
    item insSegmentErrors : CountPoint {
        :>> mnemonic = "INS_SEGMENT_ERRORS"; :>> pointId = 7019; :>> source = ApplicationName::inspectorHandling; :>> apidClass = ApidClass::imaging;
        :>> kind = TelemetryKind::engineering; :>> rate = 1.0 [Hz];
        :>> redLow = 0; :>> yellowLow = 0; :>> yellowHigh = 50; :>> redHigh = 500;
    }
    item insRelayMargin : FractionPoint {
        :>> mnemonic = "INS_RELAY_MARGIN"; :>> pointId = 7020; :>> source = ApplicationName::inspectorHandling; :>> apidClass = ApidClass::imaging;
        :>> kind = TelemetryKind::housekeeping; :>> rate = 1.0 [Hz];
        :>> redLow = 0.0; :>> yellowLow = 3.0; :>> yellowHigh = 30.0; :>> redHigh = 40.0;
    }
    item insCamT01 : TemperaturePoint {
        :>> mnemonic = "INS_CAM_T_01"; :>> pointId = 7021; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insCamT02 : TemperaturePoint {
        :>> mnemonic = "INS_CAM_T_02"; :>> pointId = 7022; :>> source = ApplicationName::inspectorHandling; :>> apidClass = ApidClass::imaging;
        :>> kind = TelemetryKind::engineering; :>> rate = 0.1 [Hz];
        :>> redLow = 233.0 [K]; :>> yellowLow = 253.0 [K]; :>> yellowHigh = 313.0 [K]; :>> redHigh = 333.0 [K];
    }
    item insCamState01 : StatusPoint {
        :>> mnemonic = "INS_CAM_STATE_01"; :>> pointId = 7023; :>> source = ApplicationName::inspectorHandling; :>> apidClass = ApidClass::imaging;
        :>> kind = TelemetryKind::engineering; :>> rate = 1.0 [Hz];
        :>> redLow = 0; :>> yellowLow = 0; :>> yellowHigh = 254; :>> redHigh = 255;
    }
    item insCamState02 : StatusPoint {
        :>> mnemonic = "INS_CAM_STATE_02"; :>> pointId = 7024; :>> source = ApplicationName::inspectorHandling; :>> apidClass = ApidClass::imaging;
        :>> kind = TelemetryKind::engineering; :>> rate = 1.0 [Hz];
        :>> redLow = 0; :>> yellowLow = 0; :>> yellowHigh = 254; :>> redHigh = 255;
    }
    item insInspPropellant : FractionPoint {
        :>> mnemonic = "INS_INSP_PROPELLANT"; :>> pointId = 7025; :>> source = ApplicationName::inspectorHandling; :>> apidClass = ApidClass::imaging;
        :>> kind = TelemetryKind::housekeeping; :>> rate = 0.1 [Hz];
        :>> redLow = 0.0; :>> yellowLow = 0.1; :>> yellowHigh = 1.0; :>> redHigh = 1.0;
    }
    item insInspThrPulses01 : CountPoint {
        :>> mnemonic = "INS_INSP_THR_PULSES_01"; :>> pointId = 7026; :>> source = ApplicationName::inspectorHandling; :>> apidClass = ApidClass::imaging;
        :>> kind = TelemetryKind::engineering; :>> rate = 0.1 [Hz];
        :>> redLow = 0; :>> yellowLow = 0; :>> yellowHigh = 61035 * 65536 + 10240; :>> redHigh = 65535 * 65536 + 65535;
    }
    item insInspThrPulses02 : CountPoint {
        :>> mnemonic = "INS_INSP_THR_PULSES_02"; :>> pointId = 7027; :>> source = ApplicationName::inspectorHandling; :>> apidClass = ApidClass::imaging;
        :>> kind = TelemetryKind::engineering; :>> rate = 0.1 [Hz];
        :>> redLow = 0; :>> yellowLow = 0; :>> yellowHigh = 61035 * 65536 + 10240; :>> redHigh = 65535 * 65536 + 65535;
    }
    item insInspThrPulses03 : CountPoint {
        :>> mnemonic = "INS_INSP_THR_PULSES_03"; :>> pointId = 7028; :>> source = ApplicationName::inspectorHandling; :>> apidClass = ApidClass::imaging;
        :>> kind = TelemetryKind::engineering; :>> rate = 0.1 [Hz];
        :>> redLow = 0; :>> yellowLow = 0; :>> yellowHigh = 61035 * 65536 + 10240; :>> redHigh = 65535 * 65536 + 65535;
    }
    item insInspThrPulses04 : CountPoint {
        :>> mnemonic = "INS_INSP_THR_PULSES_04"; :>> pointId = 7029; :>> source = ApplicationName::inspectorHandling; :>> apidClass = ApidClass::imaging;
        :>> kind = TelemetryKind::engineering; :>> rate = 0.1 [Hz];
        :>> redLow = 0; :>> yellowLow = 0; :>> yellowHigh = 61035 * 65536 + 10240; :>> redHigh = 65535 * 65536 + 65535;
    }
    item insInspThrPulses05 : CountPoint {
        :>> mnemonic = "INS_INSP_THR_PULSES_05"; :>> pointId = 7030; :>> source = ApplicationName::inspectorHandling; :>> apidClass = ApidClass::imaging;
        :>> kind = TelemetryKind::engineering; :>> rate = 0.1 [Hz];
        :>> redLow = 0; :>> yellowLow = 0; :>> yellowHigh = 61035 * 65536 + 10240; :>> redHigh = 65535 * 65536 + 65535;
    }
    item insInspThrPulses06 : CountPoint {
        :>> mnemonic = "INS_INSP_THR_PULSES_06"; :>> pointId = 7031; :>> source = ApplicationName::inspectorHandling; :>> apidClass = ApidClass::imaging;
        :>> kind = TelemetryKind::engineering; :>> rate = 0.1 [Hz];
        :>> redLow = 0; :>> yellowLow = 0; :>> yellowHigh = 61035 * 65536 + 10240; :>> redHigh = 65535 * 65536 + 65535;
    }
    item insInspThrPulses07 : CountPoint {
        :>> mnemonic = "INS_INSP_THR_PULSES_07"; :>> pointId = 7032; :>> source = ApplicationName::inspectorHandling; :>> apidClass = ApidClass::imaging;
        :>> kind = TelemetryKind::engineering; :>> rate = 0.1 [Hz];
        :>> redLow = 0; :>> yellowLow = 0; :>> yellowHigh = 61035 * 65536 + 10240; :>> redHigh = 65535 * 65536 + 65535;
    }
    item insInspThrPulses08 : CountPoint {
        :>> mnemonic = "INS_INSP_THR_PULSES_08"; :>> pointId = 7033; :>> source = ApplicationName::inspectorHandling; :>> apidClass = ApidClass::imaging;
        :>> kind = TelemetryKind::engineering; :>> rate = 0.1 [Hz];
        :>> redLow = 0; :>> yellowLow = 0; :>> yellowHigh = 61035 * 65536 + 10240; :>> redHigh = 65535 * 65536 + 65535;
    }
    item insReleaseMechState : StatusPoint {
        :>> mnemonic = "INS_RELEASE_MECH_STATE"; :>> pointId = 7034; :>> source = ApplicationName::inspectorHandling; :>> apidClass = ApidClass::imaging;
        :>> kind = TelemetryKind::housekeeping; :>> rate = 1.0 [Hz];
        :>> redLow = 0; :>> yellowLow = 0; :>> yellowHigh = 3; :>> redHigh = 3;
    }
    item insReleaseArmed : StatusPoint {
        :>> mnemonic = "INS_RELEASE_ARMED"; :>> pointId = 7035; :>> source = ApplicationName::inspectorHandling; :>> apidClass = ApidClass::imaging;
        :>> kind = TelemetryKind::housekeeping; :>> rate = 1.0 [Hz];
        :>> redLow = 0; :>> yellowLow = 0; :>> yellowHigh = 1; :>> redHigh = 1;
    }
    item insLastContactAge : DurationPoint {
        :>> mnemonic = "INS_LAST_CONTACT_AGE"; :>> pointId = 7036; :>> source = ApplicationName::inspectorHandling; :>> apidClass = ApidClass::imaging;
        :>> kind = TelemetryKind::housekeeping; :>> rate = 0.1 [Hz];
        :>> redLow = 0.0 [s]; :>> yellowLow = 0.0 [s]; :>> yellowHigh = 7200.0 [s]; :>> redHigh = 86400.0 [s];
    }
    item insImageCompression : StatusPoint {
        :>> mnemonic = "INS_IMAGE_COMPRESSION"; :>> pointId = 7037; :>> source = ApplicationName::inspectorHandling; :>> apidClass = ApidClass::imaging;
        :>> kind = TelemetryKind::engineering; :>> rate = 0.1 [Hz];
        :>> redLow = 0; :>> yellowLow = 0; :>> yellowHigh = 254; :>> redHigh = 255;
    }
    item capBagDeployPos01 : FractionPoint {
        :>> mnemonic = "CAP_BAG_DEPLOY_POS_01"; :>> pointId = 8001; :>> source = ApplicationName::captureControl; :>> apidClass = ApidClass::capture;
        :>> kind = TelemetryKind::housekeeping; :>> rate = 1.0 [Hz];
        :>> redLow = 0.0; :>> yellowLow = 0.1; :>> yellowHigh = 0.9; :>> redHigh = 1.0;
    }
    item capBagDeployPos02 : FractionPoint {
        :>> mnemonic = "CAP_BAG_DEPLOY_POS_02"; :>> pointId = 8002; :>> source = ApplicationName::captureControl; :>> apidClass = ApidClass::capture;
        :>> kind = TelemetryKind::housekeeping; :>> rate = 1.0 [Hz];
        :>> redLow = 0.0; :>> yellowLow = 0.1; :>> yellowHigh = 0.9; :>> redHigh = 1.0;
    }
    item capBagDeployPos03 : FractionPoint {
        :>> mnemonic = "CAP_BAG_DEPLOY_POS_03"; :>> pointId = 8003; :>> source = ApplicationName::captureControl; :>> apidClass = ApidClass::capture;
        :>> kind = TelemetryKind::housekeeping; :>> rate = 1.0 [Hz];
        :>> redLow = 0.0; :>> yellowLow = 0.1; :>> yellowHigh = 0.9; :>> redHigh = 1.0;
    }
    item capBagDeployPos04 : FractionPoint {
        :>> mnemonic = "CAP_BAG_DEPLOY_POS_04"; :>> pointId = 8004; :>> source = ApplicationName::captureControl; :>> apidClass = ApidClass::capture;
        :>> kind = TelemetryKind::housekeeping; :>> rate = 1.0 [Hz];
        :>> redLow = 0.0; :>> yellowLow = 0.1; :>> yellowHigh = 0.9; :>> redHigh = 1.0;
    }
    item capPetalAngle01 : AnglePoint {
        :>> mnemonic = "CAP_PETAL_ANGLE_01"; :>> pointId = 8005; :>> source = ApplicationName::captureControl; :>> apidClass = ApidClass::capture;
        :>> kind = TelemetryKind::housekeeping; :>> rate = 1.0 [Hz];
        :>> redLow = -0.1 [rad]; :>> yellowLow = 0.0 [rad]; :>> yellowHigh = 2.0 [rad]; :>> redHigh = 2.1 [rad];
    }
    item capPetalAngle02 : AnglePoint {
        :>> mnemonic = "CAP_PETAL_ANGLE_02"; :>> pointId = 8006; :>> source = ApplicationName::captureControl; :>> apidClass = ApidClass::capture;
        :>> kind = TelemetryKind::housekeeping; :>> rate = 1.0 [Hz];
        :>> redLow = -0.1 [rad]; :>> yellowLow = 0.0 [rad]; :>> yellowHigh = 2.0 [rad]; :>> redHigh = 2.1 [rad];
    }
    item capPetalAngle03 : AnglePoint {
        :>> mnemonic = "CAP_PETAL_ANGLE_03"; :>> pointId = 8007; :>> source = ApplicationName::captureControl; :>> apidClass = ApidClass::capture;
        :>> kind = TelemetryKind::housekeeping; :>> rate = 1.0 [Hz];
        :>> redLow = -0.1 [rad]; :>> yellowLow = 0.0 [rad]; :>> yellowHigh = 2.0 [rad]; :>> redHigh = 2.1 [rad];
    }
    item capPetalAngle04 : AnglePoint {
        :>> mnemonic = "CAP_PETAL_ANGLE_04"; :>> pointId = 8008; :>> source = ApplicationName::captureControl; :>> apidClass = ApidClass::capture;
        :>> kind = TelemetryKind::housekeeping; :>> rate = 1.0 [Hz];
        :>> redLow = -0.1 [rad]; :>> yellowLow = 0.0 [rad]; :>> yellowHigh = 2.0 [rad]; :>> redHigh = 2.1 [rad];
    }
    item capPetalMotorI01 : CurrentPoint {
        :>> mnemonic = "CAP_PETAL_MOTOR_I_01"; :>> pointId = 8009; :>> source = ApplicationName::captureControl; :>> apidClass = ApidClass::capture;
        :>> kind = TelemetryKind::engineering; :>> rate = 1.0 [Hz];
        :>> redLow = 0.0 [A]; :>> yellowLow = 0.0 [A]; :>> yellowHigh = 4.0 [A]; :>> redHigh = 5.0 [A];
    }
    item capPetalMotorI02 : CurrentPoint {
        :>> mnemonic = "CAP_PETAL_MOTOR_I_02"; :>> pointId = 8010; :>> source = ApplicationName::captureControl; :>> apidClass = ApidClass::capture;
        :>> kind = TelemetryKind::engineering; :>> rate = 1.0 [Hz];
        :>> redLow = 0.0 [A]; :>> yellowLow = 0.0 [A]; :>> yellowHigh = 4.0 [A]; :>> redHigh = 5.0 [A];
    }
    item capPetalMotorI03 : CurrentPoint {
        :>> mnemonic = "CAP_PETAL_MOTOR_I_03"; :>> pointId = 8011; :>> source = ApplicationName::captureControl; :>> apidClass = ApidClass::capture;
        :>> kind = TelemetryKind::engineering; :>> rate = 1.0 [Hz];
        :>> redLow = 0.0 [A]; :>> yellowLow = 0.0 [A]; :>> yellowHigh = 4.0 [A]; :>> redHigh = 5.0 [A];
    }
    item capPetalMotorI04 : CurrentPoint {
        :>> mnemonic = "CAP_PETAL_MOTOR_I_04"; :>> pointId = 8012; :>> source = ApplicationName::captureControl; :>> apidClass = ApidClass::capture;
        :>> kind = TelemetryKind::engineering; :>> rate = 1.0 [Hz];
        :>> redLow = 0.0 [A]; :>> yellowLow = 0.0 [A]; :>> yellowHigh = 4.0 [A]; :>> redHigh = 5.0 [A];
    }
    item capPetalT01 : TemperaturePoint {
        :>> mnemonic = "CAP_PETAL_T_01"; :>> pointId = 8013; :>> source = ApplicationName::captureControl; :>> apidClass = ApidClass::capture;
        :>> kind = TelemetryKind::engineering; :>> rate = 0.1 [Hz];
        :>> redLow = 233.0 [K]; :>> yellowLow = 253.0 [K]; :>> yellowHigh = 313.0 [K]; :>> redHigh = 333.0 [K];
    }
    item capPetalT02 : TemperaturePoint {
        :>> mnemonic = "CAP_PETAL_T_02"; :>> pointId = 8014; :>> source = ApplicationName::captureControl; :>> apidClass = ApidClass::capture;
        :>> kind = TelemetryKind::engineering; :>> rate = 0.1 [Hz];
        :>> redLow = 233.0 [K]; :>> yellowLow = 253.0 [K]; :>> yellowHigh = 313.0 [K]; :>> redHigh = 333.0 [K];
    }
    item capPetalT03 : TemperaturePoint {
        :>> mnemonic = "CAP_PETAL_T_03"; :>> pointId = 8015; :>> source = ApplicationName::captureControl; :>> apidClass = ApidClass::capture;
        :>> kind = TelemetryKind::engineering; :>> rate = 0.1 [Hz];
        :>> redLow = 233.0 [K]; :>> yellowLow = 253.0 [K]; :>> yellowHigh = 313.0 [K]; :>> redHigh = 333.0 [K];
    }
    item capPetalT04 : TemperaturePoint {
        :>> mnemonic = "CAP_PETAL_T_04"; :>> pointId = 8016; :>> source = ApplicationName::captureControl; :>> apidClass = ApidClass::capture;
        :>> kind = TelemetryKind::engineering; :>> rate = 0.1 [Hz];
        :>> redLow = 233.0 [K]; :>> yellowLow = 253.0 [K]; :>> yellowHigh = 313.0 [K]; :>> redHigh = 333.0 [K];
    }
    item capCinchTension01 : ForcePoint {
        :>> mnemonic = "CAP_CINCH_TENSION_01"; :>> pointId = 8017; :>> source = ApplicationName::captureControl; :>> apidClass = ApidClass::capture;
        :>> kind = TelemetryKind::housekeeping; :>> rate = 1.0 [Hz];
        :>> redLow = 0.0 [N]; :>> yellowLow = 0.0 [N]; :>> yellowHigh = 2000.0 [N]; :>> redHigh = 2500.0 [N];
    }
    item capCinchTension02 : ForcePoint {
        :>> mnemonic = "CAP_CINCH_TENSION_02"; :>> pointId = 8018; :>> source = ApplicationName::captureControl; :>> apidClass = ApidClass::capture;
        :>> kind = TelemetryKind::housekeeping; :>> rate = 1.0 [Hz];
        :>> redLow = 0.0 [N]; :>> yellowLow = 0.0 [N]; :>> yellowHigh = 2000.0 [N]; :>> redHigh = 2500.0 [N];
    }
    item capLatchState01 : StatusPoint {
        :>> mnemonic = "CAP_LATCH_STATE_01"; :>> pointId = 8019; :>> source = ApplicationName::captureControl; :>> apidClass = ApidClass::capture;
        :>> kind = TelemetryKind::housekeeping; :>> rate = 1.0 [Hz];
        :>> redLow = 0; :>> yellowLow = 0; :>> yellowHigh = 1; :>> redHigh = 1;
    }
    item capLatchState02 : StatusPoint {
        :>> mnemonic = "CAP_LATCH_STATE_02"; :>> pointId = 8020; :>> source = ApplicationName::captureControl; :>> apidClass = ApidClass::capture;
        :>> kind = TelemetryKind::housekeeping; :>> rate = 1.0 [Hz];
        :>> redLow = 0; :>> yellowLow = 0; :>> yellowHigh = 1; :>> redHigh = 1;
    }
    item capLatchState03 : StatusPoint {
        :>> mnemonic = "CAP_LATCH_STATE_03"; :>> pointId = 8021; :>> source = ApplicationName::captureControl; :>> apidClass = ApidClass::capture;
        :>> kind = TelemetryKind::housekeeping; :>> rate = 1.0 [Hz];
        :>> redLow = 0; :>> yellowLow = 0; :>> yellowHigh = 1; :>> redHigh = 1;
    }
    item capLatchState04 : StatusPoint {
        :>> mnemonic = "CAP_LATCH_STATE_04"; :>> pointId = 8022; :>> source = ApplicationName::captureControl; :>> apidClass = ApidClass::capture;
        :>> kind = TelemetryKind::housekeeping; :>> rate = 1.0 [Hz];
        :>> redLow = 0; :>> yellowLow = 0; :>> yellowHigh = 1; :>> redHigh = 1;
    }
    item capProxRange01 : LengthPoint {
        :>> mnemonic = "CAP_PROX_RANGE_01"; :>> pointId = 8023; :>> source = ApplicationName::captureControl; :>> apidClass = ApidClass::capture;
        :>> kind = TelemetryKind::engineering; :>> rate = 10.0 [Hz];
        :>> redLow = 0.0 [m]; :>> yellowLow = 0.5 [m]; :>> yellowHigh = 1000.0 [m]; :>> redHigh = 2000.0 [m];
    }
    item capProxRange02 : LengthPoint {
        :>> mnemonic = "CAP_PROX_RANGE_02"; :>> pointId = 8024; :>> source = ApplicationName::captureControl; :>> apidClass = ApidClass::capture;
        :>> kind = TelemetryKind::engineering; :>> rate = 10.0 [Hz];
        :>> redLow = 0.0 [m]; :>> yellowLow = 0.5 [m]; :>> yellowHigh = 1000.0 [m]; :>> redHigh = 2000.0 [m];
    }
    item capProxRange03 : LengthPoint {
        :>> mnemonic = "CAP_PROX_RANGE_03"; :>> pointId = 8025; :>> source = ApplicationName::captureControl; :>> apidClass = ApidClass::capture;
        :>> kind = TelemetryKind::engineering; :>> rate = 10.0 [Hz];
        :>> redLow = 0.0 [m]; :>> yellowLow = 0.5 [m]; :>> yellowHigh = 1000.0 [m]; :>> redHigh = 2000.0 [m];
    }
    item capProxRange04 : LengthPoint {
        :>> mnemonic = "CAP_PROX_RANGE_04"; :>> pointId = 8026; :>> source = ApplicationName::captureControl; :>> apidClass = ApidClass::capture;
        :>> kind = TelemetryKind::engineering; :>> rate = 10.0 [Hz];
        :>> redLow = 0.0 [m]; :>> yellowLow = 0.5 [m]; :>> yellowHigh = 1000.0 [m]; :>> redHigh = 2000.0 [m];
    }
    item capProxRange05 : LengthPoint {
        :>> mnemonic = "CAP_PROX_RANGE_05"; :>> pointId = 8027; :>> source = ApplicationName::captureControl; :>> apidClass = ApidClass::capture;
        :>> kind = TelemetryKind::engineering; :>> rate = 10.0 [Hz];
        :>> redLow = 0.0 [m]; :>> yellowLow = 0.5 [m]; :>> yellowHigh = 1000.0 [m]; :>> redHigh = 2000.0 [m];
    }
    item capProxRange06 : LengthPoint {
        :>> mnemonic = "CAP_PROX_RANGE_06"; :>> pointId = 8028; :>> source = ApplicationName::captureControl; :>> apidClass = ApidClass::capture;
        :>> kind = TelemetryKind::engineering; :>> rate = 10.0 [Hz];
        :>> redLow = 0.0 [m]; :>> yellowLow = 0.5 [m]; :>> yellowHigh = 1000.0 [m]; :>> redHigh = 2000.0 [m];
    }
    item capProxRange07 : LengthPoint {
        :>> mnemonic = "CAP_PROX_RANGE_07"; :>> pointId = 8029; :>> source = ApplicationName::captureControl; :>> apidClass = ApidClass::capture;
        :>> kind = TelemetryKind::engineering; :>> rate = 10.0 [Hz];
        :>> redLow = 0.0 [m]; :>> yellowLow = 0.5 [m]; :>> yellowHigh = 1000.0 [m]; :>> redHigh = 2000.0 [m];
    }
    item capProxRange08 : LengthPoint {
        :>> mnemonic = "CAP_PROX_RANGE_08"; :>> pointId = 8030; :>> source = ApplicationName::captureControl; :>> apidClass = ApidClass::capture;
        :>> kind = TelemetryKind::engineering; :>> rate = 10.0 [Hz];
        :>> redLow = 0.0 [m]; :>> yellowLow = 0.5 [m]; :>> yellowHigh = 1000.0 [m]; :>> redHigh = 2000.0 [m];
    }
    item capProxState01 : StatusPoint {
        :>> mnemonic = "CAP_PROX_STATE_01"; :>> pointId = 8031; :>> source = ApplicationName::captureControl; :>> apidClass = ApidClass::capture;
        :>> kind = TelemetryKind::engineering; :>> rate = 1.0 [Hz];
        :>> redLow = 0; :>> yellowLow = 0; :>> yellowHigh = 254; :>> redHigh = 255;
    }
    item capProxState02 : StatusPoint {
        :>> mnemonic = "CAP_PROX_STATE_02"; :>> pointId = 8032; :>> source = ApplicationName::captureControl; :>> apidClass = ApidClass::capture;
        :>> kind = TelemetryKind::engineering; :>> rate = 1.0 [Hz];
        :>> redLow = 0; :>> yellowLow = 0; :>> yellowHigh = 254; :>> redHigh = 255;
    }
    item capProxState03 : StatusPoint {
        :>> mnemonic = "CAP_PROX_STATE_03"; :>> pointId = 8033; :>> source = ApplicationName::captureControl; :>> apidClass = ApidClass::capture;
        :>> kind = TelemetryKind::engineering; :>> rate = 1.0 [Hz];
        :>> redLow = 0; :>> yellowLow = 0; :>> yellowHigh = 254; :>> redHigh = 255;
    }
    item capProxState04 : StatusPoint {
        :>> mnemonic = "CAP_PROX_STATE_04"; :>> pointId = 8034; :>> source = ApplicationName::captureControl; :>> apidClass = ApidClass::capture;
        :>> kind = TelemetryKind::engineering; :>> rate = 1.0 [Hz];
        :>> redLow = 0; :>> yellowLow = 0; :>> yellowHigh = 254; :>> redHigh = 255;
    }
    item capProxState05 : StatusPoint {
        :>> mnemonic = "CAP_PROX_STATE_05"; :>> pointId = 8035; :>> source = ApplicationName::captureControl; :>> apidClass = ApidClass::capture;
        :>> kind = TelemetryKind::engineering; :>> rate = 1.0 [Hz];
        :>> redLow = 0; :>> yellowLow = 0; :>> yellowHigh = 254; :>> redHigh = 255;
    }
    item capProxState06 : StatusPoint {
        :>> mnemonic = "CAP_PROX_STATE_06"; :>> pointId = 8036; :>> source = ApplicationName::captureControl; :>> apidClass = ApidClass::capture;
        :>> kind = TelemetryKind::engineering; :>> rate = 1.0 [Hz];
        :>> redLow = 0; :>> yellowLow = 0; :>> yellowHigh = 254; :>> redHigh = 255;
    }
    item capProxState07 : StatusPoint {
        :>> mnemonic = "CAP_PROX_STATE_07"; :>> pointId = 8037; :>> source = ApplicationName::captureControl; :>> apidClass = ApidClass::capture;
        :>> kind = TelemetryKind::engineering; :>> rate = 1.0 [Hz];
        :>> redLow = 0; :>> yellowLow = 0; :>> yellowHigh = 254; :>> redHigh = 255;
    }
    item capProxState08 : StatusPoint {
        :>> mnemonic = "CAP_PROX_STATE_08"; :>> pointId = 8038; :>> source = ApplicationName::captureControl; :>> apidClass = ApidClass::capture;
        :>> kind = TelemetryKind::engineering; :>> rate = 1.0 [Hz];
        :>> redLow = 0; :>> yellowLow = 0; :>> yellowHigh = 254; :>> redHigh = 255;
    }
    item capBodySpinRate01 : AngularRatePoint {
        :>> mnemonic = "CAP_BODY_SPIN_RATE_01"; :>> pointId = 8039; :>> source = ApplicationName::captureControl; :>> apidClass = ApidClass::capture;
        :>> kind = TelemetryKind::housekeeping; :>> rate = 1.0 [Hz];
        :>> redLow = -0.6 [rad/s]; :>> yellowLow = -0.5 [rad/s]; :>> yellowHigh = 0.5 [rad/s]; :>> redHigh = 0.6 [rad/s];
    }
    item capBodySpinRate02 : AngularRatePoint {
        :>> mnemonic = "CAP_BODY_SPIN_RATE_02"; :>> pointId = 8040; :>> source = ApplicationName::captureControl; :>> apidClass = ApidClass::capture;
        :>> kind = TelemetryKind::housekeeping; :>> rate = 1.0 [Hz];
        :>> redLow = -0.6 [rad/s]; :>> yellowLow = -0.5 [rad/s]; :>> yellowHigh = 0.5 [rad/s]; :>> redHigh = 0.6 [rad/s];
    }
    item capBodySpinRate03 : AngularRatePoint {
        :>> mnemonic = "CAP_BODY_SPIN_RATE_03"; :>> pointId = 8041; :>> source = ApplicationName::captureControl; :>> apidClass = ApidClass::capture;
        :>> kind = TelemetryKind::housekeeping; :>> rate = 1.0 [Hz];
        :>> redLow = -0.6 [rad/s]; :>> yellowLow = -0.5 [rad/s]; :>> yellowHigh = 0.5 [rad/s]; :>> redHigh = 0.6 [rad/s];
    }
    item capDespinTorque : FractionPoint {
        :>> mnemonic = "CAP_DESPIN_TORQUE"; :>> pointId = 8042; :>> source = ApplicationName::captureControl; :>> apidClass = ApidClass::capture;
        :>> kind = TelemetryKind::housekeeping; :>> rate = 1.0 [Hz];
        :>> redLow = 0.0; :>> yellowLow = 0.1; :>> yellowHigh = 0.9; :>> redHigh = 1.0;
    }
    item capDespinProgress : FractionPoint {
        :>> mnemonic = "CAP_DESPIN_PROGRESS"; :>> pointId = 8043; :>> source = ApplicationName::captureControl; :>> apidClass = ApidClass::capture;
        :>> kind = TelemetryKind::housekeeping; :>> rate = 0.1 [Hz];
        :>> redLow = 0.0; :>> yellowLow = 0.1; :>> yellowHigh = 0.9; :>> redHigh = 1.0;
    }
    item capCaptureArmed : StatusPoint {
        :>> mnemonic = "CAP_CAPTURE_ARMED"; :>> pointId = 8044; :>> source = ApplicationName::captureControl; :>> apidClass = ApidClass::capture;
        :>> kind = TelemetryKind::housekeeping; :>> rate = 1.0 [Hz];
        :>> redLow = 0; :>> yellowLow = 0; :>> yellowHigh = 1; :>> redHigh = 1;
    }
    item capCaptureState : StatusPoint {
        :>> mnemonic = "CAP_CAPTURE_STATE"; :>> pointId = 8045; :>> source = ApplicationName::captureControl; :>> apidClass = ApidClass::capture;
        :>> kind = TelemetryKind::housekeeping; :>> rate = 1.0 [Hz];
        :>> redLow = 0; :>> yellowLow = 0; :>> yellowHigh = 254; :>> redHigh = 255;
    }
    item capContactForce01 : ForcePoint {
        :>> mnemonic = "CAP_CONTACT_FORCE_01"; :>> pointId = 8046; :>> source = ApplicationName::captureControl; :>> apidClass = ApidClass::capture;
        :>> kind = TelemetryKind::housekeeping; :>> rate = 10.0 [Hz];
        :>> redLow = -500.0 [N]; :>> yellowLow = -400.0 [N]; :>> yellowHigh = 400.0 [N]; :>> redHigh = 500.0 [N];
    }
    item capContactForce02 : ForcePoint {
        :>> mnemonic = "CAP_CONTACT_FORCE_02"; :>> pointId = 8047; :>> source = ApplicationName::captureControl; :>> apidClass = ApidClass::capture;
        :>> kind = TelemetryKind::housekeeping; :>> rate = 10.0 [Hz];
        :>> redLow = -500.0 [N]; :>> yellowLow = -400.0 [N]; :>> yellowHigh = 400.0 [N]; :>> redHigh = 500.0 [N];
    }
    item capContactForce03 : ForcePoint {
        :>> mnemonic = "CAP_CONTACT_FORCE_03"; :>> pointId = 8048; :>> source = ApplicationName::captureControl; :>> apidClass = ApidClass::capture;
        :>> kind = TelemetryKind::housekeeping; :>> rate = 10.0 [Hz];
        :>> redLow = -500.0 [N]; :>> yellowLow = -400.0 [N]; :>> yellowHigh = 400.0 [N]; :>> redHigh = 500.0 [N];
    }
    item capBodyMassEst : MassPoint {
        :>> mnemonic = "CAP_BODY_MASS_EST"; :>> pointId = 8049; :>> source = ApplicationName::captureControl; :>> apidClass = ApidClass::capture;
        :>> kind = TelemetryKind::housekeeping; :>> rate = 0.01 [Hz];
        :>> redLow = 0.0 [kg]; :>> yellowLow = 1000.0 [kg]; :>> yellowHigh = 2000000.0 [kg]; :>> redHigh = 2500000.0 [kg];
    }
    item capApproachRate : SpeedPoint {
        :>> mnemonic = "CAP_APPROACH_RATE"; :>> pointId = 8050; :>> source = ApplicationName::captureControl; :>> apidClass = ApidClass::capture;
        :>> kind = TelemetryKind::housekeeping; :>> rate = 1.0 [Hz];
        :>> redLow = -1.0 [m/s]; :>> yellowLow = -0.5 [m/s]; :>> yellowHigh = 0.5 [m/s]; :>> redHigh = 1.0 [m/s];
    }
    item capMechanismT01 : TemperaturePoint {
        :>> mnemonic = "CAP_MECHANISM_T_01"; :>> pointId = 8051; :>> source = ApplicationName::captureControl; :>> apidClass = ApidClass::capture;
        :>> kind = TelemetryKind::engineering; :>> rate = 0.1 [Hz];
        :>> redLow = 233.0 [K]; :>> yellowLow = 253.0 [K]; :>> yellowHigh = 313.0 [K]; :>> redHigh = 333.0 [K];
    }
    item capMechanismT02 : TemperaturePoint {
        :>> mnemonic = "CAP_MECHANISM_T_02"; :>> pointId = 8052; :>> source = ApplicationName::captureControl; :>> apidClass = ApidClass::capture;
        :>> kind = TelemetryKind::engineering; :>> rate = 0.1 [Hz];
        :>> redLow = 233.0 [K]; :>> yellowLow = 253.0 [K]; :>> yellowHigh = 313.0 [K]; :>> redHigh = 333.0 [K];
    }
    item capMechanismT03 : TemperaturePoint {
        :>> mnemonic = "CAP_MECHANISM_T_03"; :>> pointId = 8053; :>> source = ApplicationName::captureControl; :>> apidClass = ApidClass::capture;
        :>> kind = TelemetryKind::engineering; :>> rate = 0.1 [Hz];
        :>> redLow = 233.0 [K]; :>> yellowLow = 253.0 [K]; :>> yellowHigh = 313.0 [K]; :>> redHigh = 333.0 [K];
    }
    item capMechanismT04 : TemperaturePoint {
        :>> mnemonic = "CAP_MECHANISM_T_04"; :>> pointId = 8054; :>> source = ApplicationName::captureControl; :>> apidClass = ApidClass::capture;
        :>> kind = TelemetryKind::engineering; :>> rate = 0.1 [Hz];
        :>> redLow = 233.0 [K]; :>> yellowLow = 253.0 [K]; :>> yellowHigh = 313.0 [K]; :>> redHigh = 333.0 [K];
    }
    item autSeqState01 : StatusPoint {
        :>> mnemonic = "AUT_SEQ_STATE_01"; :>> pointId = 9001; :>> source = ApplicationName::autonomy; :>> apidClass = ApidClass::guidance;
        :>> kind = TelemetryKind::housekeeping; :>> rate = 1.0 [Hz];
        :>> redLow = 0; :>> yellowLow = 0; :>> yellowHigh = 254; :>> redHigh = 255;
    }
    item autSeqState02 : StatusPoint {
        :>> mnemonic = "AUT_SEQ_STATE_02"; :>> pointId = 9002; :>> source = ApplicationName::autonomy; :>> apidClass = ApidClass::guidance;
        :>> kind = TelemetryKind::housekeeping; :>> rate = 1.0 [Hz];
        :>> redLow = 0; :>> yellowLow = 0; :>> yellowHigh = 254; :>> redHigh = 255;
    }
    item autSeqState03 : StatusPoint {
        :>> mnemonic = "AUT_SEQ_STATE_03"; :>> pointId = 9003; :>> source = ApplicationName::autonomy; :>> apidClass = ApidClass::guidance;
        :>> kind = TelemetryKind::housekeeping; :>> rate = 1.0 [Hz];
        :>> redLow = 0; :>> yellowLow = 0; :>> yellowHigh = 254; :>> redHigh = 255;
    }
    item autSeqState04 : StatusPoint {
        :>> mnemonic = "AUT_SEQ_STATE_04"; :>> pointId = 9004; :>> source = ApplicationName::autonomy; :>> apidClass = ApidClass::guidance;
        :>> kind = TelemetryKind::housekeeping; :>> rate = 1.0 [Hz];
        :>> redLow = 0; :>> yellowLow = 0; :>> yellowHigh = 254; :>> redHigh = 255;
    }
    item autSeqStep01 : CountPoint {
        :>> mnemonic = "AUT_SEQ_STEP_01"; :>> pointId = 9005; :>> source = ApplicationName::autonomy; :>> apidClass = ApidClass::guidance;
        :>> kind = TelemetryKind::housekeeping; :>> rate = 1.0 [Hz];
        :>> redLow = 0; :>> yellowLow = 0; :>> yellowHigh = 61035 * 65536 + 10240; :>> redHigh = 65535 * 65536 + 65535;
    }
    item autSeqStep02 : CountPoint {
        :>> mnemonic = "AUT_SEQ_STEP_02"; :>> pointId = 9006; :>> source = ApplicationName::autonomy; :>> apidClass = ApidClass::guidance;
        :>> kind = TelemetryKind::housekeeping; :>> rate = 1.0 [Hz];
        :>> redLow = 0; :>> yellowLow = 0; :>> yellowHigh = 61035 * 65536 + 10240; :>> redHigh = 65535 * 65536 + 65535;
    }
    item autSeqStep03 : CountPoint {
        :>> mnemonic = "AUT_SEQ_STEP_03"; :>> pointId = 9007; :>> source = ApplicationName::autonomy; :>> apidClass = ApidClass::guidance;
        :>> kind = TelemetryKind::housekeeping; :>> rate = 1.0 [Hz];
        :>> redLow = 0; :>> yellowLow = 0; :>> yellowHigh = 61035 * 65536 + 10240; :>> redHigh = 65535 * 65536 + 65535;
    }
    item autSeqStep04 : CountPoint {
        :>> mnemonic = "AUT_SEQ_STEP_04"; :>> pointId = 9008; :>> source = ApplicationName::autonomy; :>> apidClass = ApidClass::guidance;
        :>> kind = TelemetryKind::housekeeping; :>> rate = 1.0 [Hz];
        :>> redLow = 0; :>> yellowLow = 0; :>> yellowHigh = 61035 * 65536 + 10240; :>> redHigh = 65535 * 65536 + 65535;
    }
    item autSeqId01 : CountPoint {
        :>> mnemonic = "AUT_SEQ_ID_01"; :>> pointId = 9009; :>> source = ApplicationName::autonomy; :>> apidClass = ApidClass::guidance;
        :>> kind = TelemetryKind::housekeeping; :>> rate = 1.0 [Hz];
        :>> redLow = 0; :>> yellowLow = 0; :>> yellowHigh = 61035 * 65536 + 10240; :>> redHigh = 65535 * 65536 + 65535;
    }
    item autSeqId02 : CountPoint {
        :>> mnemonic = "AUT_SEQ_ID_02"; :>> pointId = 9010; :>> source = ApplicationName::autonomy; :>> apidClass = ApidClass::guidance;
        :>> kind = TelemetryKind::housekeeping; :>> rate = 1.0 [Hz];
        :>> redLow = 0; :>> yellowLow = 0; :>> yellowHigh = 61035 * 65536 + 10240; :>> redHigh = 65535 * 65536 + 65535;
    }
    item autSeqId03 : CountPoint {
        :>> mnemonic = "AUT_SEQ_ID_03"; :>> pointId = 9011; :>> source = ApplicationName::autonomy; :>> apidClass = ApidClass::guidance;
        :>> kind = TelemetryKind::housekeeping; :>> rate = 1.0 [Hz];
        :>> redLow = 0; :>> yellowLow = 0; :>> yellowHigh = 61035 * 65536 + 10240; :>> redHigh = 65535 * 65536 + 65535;
    }
    item autSeqId04 : CountPoint {
        :>> mnemonic = "AUT_SEQ_ID_04"; :>> pointId = 9012; :>> source = ApplicationName::autonomy; :>> apidClass = ApidClass::guidance;
        :>> kind = TelemetryKind::housekeeping; :>> rate = 1.0 [Hz];
        :>> redLow = 0; :>> yellowLow = 0; :>> yellowHigh = 61035 * 65536 + 10240; :>> redHigh = 65535 * 65536 + 65535;
    }
    item autSeqTimeToNext01 : DurationPoint {
        :>> mnemonic = "AUT_SEQ_TIME_TO_NEXT_01"; :>> pointId = 9013; :>> source = ApplicationName::autonomy; :>> apidClass = ApidClass::guidance;
        :>> kind = TelemetryKind::engineering; :>> rate = 1.0 [Hz];
        :>> redLow = 0.0 [s]; :>> yellowLow = 0.0 [s]; :>> yellowHigh = 10000000.0 [s]; :>> redHigh = 100000000.0 [s];
    }
    item autSeqTimeToNext02 : DurationPoint {
        :>> mnemonic = "AUT_SEQ_TIME_TO_NEXT_02"; :>> pointId = 9014; :>> source = ApplicationName::autonomy; :>> apidClass = ApidClass::guidance;
        :>> kind = TelemetryKind::engineering; :>> rate = 1.0 [Hz];
        :>> redLow = 0.0 [s]; :>> yellowLow = 0.0 [s]; :>> yellowHigh = 10000000.0 [s]; :>> redHigh = 100000000.0 [s];
    }
    item autSeqTimeToNext03 : DurationPoint {
        :>> mnemonic = "AUT_SEQ_TIME_TO_NEXT_03"; :>> pointId = 9015; :>> source = ApplicationName::autonomy; :>> apidClass = ApidClass::guidance;
        :>> kind = TelemetryKind::engineering; :>> rate = 1.0 [Hz];
        :>> redLow = 0.0 [s]; :>> yellowLow = 0.0 [s]; :>> yellowHigh = 10000000.0 [s]; :>> redHigh = 100000000.0 [s];
    }
    item autSeqTimeToNext04 : DurationPoint {
        :>> mnemonic = "AUT_SEQ_TIME_TO_NEXT_04"; :>> pointId = 9016; :>> source = ApplicationName::autonomy; :>> apidClass = ApidClass::guidance;
        :>> kind = TelemetryKind::engineering; :>> rate = 1.0 [Hz];
        :>> redLow = 0.0 [s]; :>> yellowLow = 0.0 [s]; :>> yellowHigh = 10000000.0 [s]; :>> redHigh = 100000000.0 [s];
    }
    item autRuleFiredCount01 : CountPoint {
        :>> mnemonic = "AUT_RULE_FIRED_COUNT_01"; :>> pointId = 9017; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount02 : CountPoint {
        :>> mnemonic = "AUT_RULE_FIRED_COUNT_02"; :>> pointId = 9018; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount03 : CountPoint {
        :>> mnemonic = "AUT_RULE_FIRED_COUNT_03"; :>> pointId = 9019; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount04 : CountPoint {
        :>> mnemonic = "AUT_RULE_FIRED_COUNT_04"; :>> pointId = 9020; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount05 : CountPoint {
        :>> mnemonic = "AUT_RULE_FIRED_COUNT_05"; :>> pointId = 9021; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount06 : CountPoint {
        :>> mnemonic = "AUT_RULE_FIRED_COUNT_06"; :>> pointId = 9022; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount07 : CountPoint {
        :>> mnemonic = "AUT_RULE_FIRED_COUNT_07"; :>> pointId = 9023; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount08 : CountPoint {
        :>> mnemonic = "AUT_RULE_FIRED_COUNT_08"; :>> pointId = 9024; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount09 : CountPoint {
        :>> mnemonic = "AUT_RULE_FIRED_COUNT_09"; :>> pointId = 9025; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount10 : CountPoint {
        :>> mnemonic = "AUT_RULE_FIRED_COUNT_10"; :>> pointId = 9026; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount11 : CountPoint {
        :>> mnemonic = "AUT_RULE_FIRED_COUNT_11"; :>> pointId = 9027; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount12 : CountPoint {
        :>> mnemonic = "AUT_RULE_FIRED_COUNT_12"; :>> pointId = 9028; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount13 : CountPoint {
        :>> mnemonic = "AUT_RULE_FIRED_COUNT_13"; :>> pointId = 9029; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount14 : CountPoint {
        :>> mnemonic = "AUT_RULE_FIRED_COUNT_14"; :>> pointId = 9030; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount15 : CountPoint {
        :>> mnemonic = "AUT_RULE_FIRED_COUNT_15"; :>> pointId = 9031; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleFiredCount16 : CountPoint {
        :>> mnemonic = "AUT_RULE_FIRED_COUNT_16"; :>> pointId = 9032; :>> source = ApplicationName::autonomy; :>> apidClass = ApidClass::guidance;
        :>> kind = TelemetryKind::engineering; :>> rate = 0.1 [Hz];
        :>> redLow = 0; :>> yellowLow = 0; :>> yellowHigh = 61035 * 65536 + 10240; :>> redHigh = 65535 * 65536 + 65535;
    }
    item autRuleEnabled01 : StatusPoint {
        :>> mnemonic = "AUT_RULE_ENABLED_01"; :>> pointId = 9033; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled02 : StatusPoint {
        :>> mnemonic = "AUT_RULE_ENABLED_02"; :>> pointId = 9034; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled03 : StatusPoint {
        :>> mnemonic = "AUT_RULE_ENABLED_03"; :>> pointId = 9035; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled04 : StatusPoint {
        :>> mnemonic = "AUT_RULE_ENABLED_04"; :>> pointId = 9036; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled05 : StatusPoint {
        :>> mnemonic = "AUT_RULE_ENABLED_05"; :>> pointId = 9037; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled06 : StatusPoint {
        :>> mnemonic = "AUT_RULE_ENABLED_06"; :>> pointId = 9038; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled07 : StatusPoint {
        :>> mnemonic = "AUT_RULE_ENABLED_07"; :>> pointId = 9039; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled08 : StatusPoint {
        :>> mnemonic = "AUT_RULE_ENABLED_08"; :>> pointId = 9040; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled09 : StatusPoint {
        :>> mnemonic = "AUT_RULE_ENABLED_09"; :>> pointId = 9041; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled10 : StatusPoint {
        :>> mnemonic = "AUT_RULE_ENABLED_10"; :>> pointId = 9042; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled11 : StatusPoint {
        :>> mnemonic = "AUT_RULE_ENABLED_11"; :>> pointId = 9043; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled12 : StatusPoint {
        :>> mnemonic = "AUT_RULE_ENABLED_12"; :>> pointId = 9044; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled13 : StatusPoint {
        :>> mnemonic = "AUT_RULE_ENABLED_13"; :>> pointId = 9045; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled14 : StatusPoint {
        :>> mnemonic = "AUT_RULE_ENABLED_14"; :>> pointId = 9046; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled15 : StatusPoint {
        :>> mnemonic = "AUT_RULE_ENABLED_15"; :>> pointId = 9047; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autRuleEnabled16 : StatusPoint {
        :>> mnemonic = "AUT_RULE_ENABLED_16"; :>> pointId = 9048; :>> source = ApplicationName::autonomy; :>> apidClass = ApidClass::guidance;
        :>> kind = TelemetryKind::engineering; :>> rate = 0.1 [Hz];
        :>> redLow = 0; :>> yellowLow = 0; :>> yellowHigh = 1; :>> redHigh = 1;
    }
    item autWaypointIndex : CountPoint {
        :>> mnemonic = "AUT_WAYPOINT_INDEX"; :>> pointId = 9049; :>> source = ApplicationName::autonomy; :>> apidClass = ApidClass::guidance;
        :>> kind = TelemetryKind::housekeeping; :>> rate = 1.0 [Hz];
        :>> redLow = 0; :>> yellowLow = 0; :>> yellowHigh = 31; :>> redHigh = 31;
    }
    item autWaypointRange : LengthPoint {
        :>> mnemonic = "AUT_WAYPOINT_RANGE"; :>> pointId = 9050; :>> source = ApplicationName::autonomy; :>> apidClass = ApidClass::guidance;
        :>> kind = TelemetryKind::housekeeping; :>> rate = 1.0 [Hz];
        :>> redLow = 0.0 [m]; :>> yellowLow = 10.0 [m]; :>> yellowHigh = 100000000.0 [m]; :>> redHigh = 1000000000.0 [m];
    }
    item autAutonomyLevel : StatusPoint {
        :>> mnemonic = "AUT_AUTONOMY_LEVEL"; :>> pointId = 9051; :>> source = ApplicationName::autonomy; :>> apidClass = ApidClass::guidance;
        :>> kind = TelemetryKind::housekeeping; :>> rate = 1.0 [Hz];
        :>> redLow = 0; :>> yellowLow = 0; :>> yellowHigh = 3; :>> redHigh = 3;
    }
    item autPlanHorizon : DurationPoint {
        :>> mnemonic = "AUT_PLAN_HORIZON"; :>> pointId = 9052; :>> source = ApplicationName::autonomy; :>> apidClass = ApidClass::guidance;
        :>> kind = TelemetryKind::engineering; :>> rate = 0.1 [Hz];
        :>> redLow = 0.0 [s]; :>> yellowLow = 0.0 [s]; :>> yellowHigh = 10000000.0 [s]; :>> redHigh = 100000000.0 [s];
    }
    item autEngineEnabled01 : StatusPoint {
        :>> mnemonic = "AUT_ENGINE_ENABLED_01"; :>> pointId = 9053; :>> source = ApplicationName::autonomy; :>> apidClass = ApidClass::guidance;
        :>> kind = TelemetryKind::housekeeping; :>> rate = 1.0 [Hz];
        :>> redLow = 0; :>> yellowLow = 0; :>> yellowHigh = 1; :>> redHigh = 1;
    }
    item autEngineEnabled02 : StatusPoint {
        :>> mnemonic = "AUT_ENGINE_ENABLED_02"; :>> pointId = 9054; :>> source = ApplicationName::autonomy; :>> apidClass = ApidClass::guidance;
        :>> kind = TelemetryKind::housekeeping; :>> rate = 1.0 [Hz];
        :>> redLow = 0; :>> yellowLow = 0; :>> yellowHigh = 1; :>> redHigh = 1;
    }
    item autEngineEnabled03 : StatusPoint {
        :>> mnemonic = "AUT_ENGINE_ENABLED_03"; :>> pointId = 9055; :>> source = ApplicationName::autonomy; :>> apidClass = ApidClass::guidance;
        :>> kind = TelemetryKind::housekeeping; :>> rate = 1.0 [Hz];
        :>> redLow = 0; :>> yellowLow = 0; :>> yellowHigh = 1; :>> redHigh = 1;
    }
    item autEngineEnabled04 : StatusPoint {
        :>> mnemonic = "AUT_ENGINE_ENABLED_04"; :>> pointId = 9056; :>> source = ApplicationName::autonomy; :>> apidClass = ApidClass::guidance;
        :>> kind = TelemetryKind::housekeeping; :>> rate = 1.0 [Hz];
        :>> redLow = 0; :>> yellowLow = 0; :>> yellowHigh = 1; :>> redHigh = 1;
    }
    item fdrMonState01 : StatusPoint {
        :>> mnemonic = "FDR_MON_STATE_01"; :>> pointId = 10001; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState02 : StatusPoint {
        :>> mnemonic = "FDR_MON_STATE_02"; :>> pointId = 10002; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState03 : StatusPoint {
        :>> mnemonic = "FDR_MON_STATE_03"; :>> pointId = 10003; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState04 : StatusPoint {
        :>> mnemonic = "FDR_MON_STATE_04"; :>> pointId = 10004; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState05 : StatusPoint {
        :>> mnemonic = "FDR_MON_STATE_05"; :>> pointId = 10005; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState06 : StatusPoint {
        :>> mnemonic = "FDR_MON_STATE_06"; :>> pointId = 10006; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState07 : StatusPoint {
        :>> mnemonic = "FDR_MON_STATE_07"; :>> pointId = 10007; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState08 : StatusPoint {
        :>> mnemonic = "FDR_MON_STATE_08"; :>> pointId = 10008; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState09 : StatusPoint {
        :>> mnemonic = "FDR_MON_STATE_09"; :>> pointId = 10009; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState10 : StatusPoint {
        :>> mnemonic = "FDR_MON_STATE_10"; :>> pointId = 10010; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState11 : StatusPoint {
        :>> mnemonic = "FDR_MON_STATE_11"; :>> pointId = 10011; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState12 : StatusPoint {
        :>> mnemonic = "FDR_MON_STATE_12"; :>> pointId = 10012; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState13 : StatusPoint {
        :>> mnemonic = "FDR_MON_STATE_13"; :>> pointId = 10013; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState14 : StatusPoint {
        :>> mnemonic = "FDR_MON_STATE_14"; :>> pointId = 10014; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState15 : StatusPoint {
        :>> mnemonic = "FDR_MON_STATE_15"; :>> pointId = 10015; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState16 : StatusPoint {
        :>> mnemonic = "FDR_MON_STATE_16"; :>> pointId = 10016; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState17 : StatusPoint {
        :>> mnemonic = "FDR_MON_STATE_17"; :>> pointId = 10017; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState18 : StatusPoint {
        :>> mnemonic = "FDR_MON_STATE_18"; :>> pointId = 10018; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState19 : StatusPoint {
        :>> mnemonic = "FDR_MON_STATE_19"; :>> pointId = 10019; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState20 : StatusPoint {
        :>> mnemonic = "FDR_MON_STATE_20"; :>> pointId = 10020; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState21 : StatusPoint {
        :>> mnemonic = "FDR_MON_STATE_21"; :>> pointId = 10021; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState22 : StatusPoint {
        :>> mnemonic = "FDR_MON_STATE_22"; :>> pointId = 10022; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState23 : StatusPoint {
        :>> mnemonic = "FDR_MON_STATE_23"; :>> pointId = 10023; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState24 : StatusPoint {
        :>> mnemonic = "FDR_MON_STATE_24"; :>> pointId = 10024; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState25 : StatusPoint {
        :>> mnemonic = "FDR_MON_STATE_25"; :>> pointId = 10025; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState26 : StatusPoint {
        :>> mnemonic = "FDR_MON_STATE_26"; :>> pointId = 10026; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState27 : StatusPoint {
        :>> mnemonic = "FDR_MON_STATE_27"; :>> pointId = 10027; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState28 : StatusPoint {
        :>> mnemonic = "FDR_MON_STATE_28"; :>> pointId = 10028; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState29 : StatusPoint {
        :>> mnemonic = "FDR_MON_STATE_29"; :>> pointId = 10029; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState30 : StatusPoint {
        :>> mnemonic = "FDR_MON_STATE_30"; :>> pointId = 10030; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState31 : StatusPoint {
        :>> mnemonic = "FDR_MON_STATE_31"; :>> pointId = 10031; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState32 : StatusPoint {
        :>> mnemonic = "FDR_MON_STATE_32"; :>> pointId = 10032; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState33 : StatusPoint {
        :>> mnemonic = "FDR_MON_STATE_33"; :>> pointId = 10033; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState34 : StatusPoint {
        :>> mnemonic = "FDR_MON_STATE_34"; :>> pointId = 10034; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState35 : StatusPoint {
        :>> mnemonic = "FDR_MON_STATE_35"; :>> pointId = 10035; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState36 : StatusPoint {
        :>> mnemonic = "FDR_MON_STATE_36"; :>> pointId = 10036; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState37 : StatusPoint {
        :>> mnemonic = "FDR_MON_STATE_37"; :>> pointId = 10037; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState38 : StatusPoint {
        :>> mnemonic = "FDR_MON_STATE_38"; :>> pointId = 10038; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState39 : StatusPoint {
        :>> mnemonic = "FDR_MON_STATE_39"; :>> pointId = 10039; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState40 : StatusPoint {
        :>> mnemonic = "FDR_MON_STATE_40"; :>> pointId = 10040; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState41 : StatusPoint {
        :>> mnemonic = "FDR_MON_STATE_41"; :>> pointId = 10041; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState42 : StatusPoint {
        :>> mnemonic = "FDR_MON_STATE_42"; :>> pointId = 10042; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState43 : StatusPoint {
        :>> mnemonic = "FDR_MON_STATE_43"; :>> pointId = 10043; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState44 : StatusPoint {
        :>> mnemonic = "FDR_MON_STATE_44"; :>> pointId = 10044; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState45 : StatusPoint {
        :>> mnemonic = "FDR_MON_STATE_45"; :>> pointId = 10045; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState46 : StatusPoint {
        :>> mnemonic = "FDR_MON_STATE_46"; :>> pointId = 10046; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState47 : StatusPoint {
        :>> mnemonic = "FDR_MON_STATE_47"; :>> pointId = 10047; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonState48 : StatusPoint {
        :>> mnemonic = "FDR_MON_STATE_48"; :>> pointId = 10048; :>> source = ApplicationName::fdir; :>> apidClass = ApidClass::housekeeping;
        :>> kind = TelemetryKind::housekeeping; :>> rate = 1.0 [Hz];
        :>> redLow = 0; :>> yellowLow = 0; :>> yellowHigh = 3; :>> redHigh = 3;
    }
    item fdrMonTripCount01 : CountPoint {
        :>> mnemonic = "FDR_MON_TRIP_COUNT_01"; :>> pointId = 10049; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount02 : CountPoint {
        :>> mnemonic = "FDR_MON_TRIP_COUNT_02"; :>> pointId = 10050; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount03 : CountPoint {
        :>> mnemonic = "FDR_MON_TRIP_COUNT_03"; :>> pointId = 10051; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount04 : CountPoint {
        :>> mnemonic = "FDR_MON_TRIP_COUNT_04"; :>> pointId = 10052; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount05 : CountPoint {
        :>> mnemonic = "FDR_MON_TRIP_COUNT_05"; :>> pointId = 10053; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount06 : CountPoint {
        :>> mnemonic = "FDR_MON_TRIP_COUNT_06"; :>> pointId = 10054; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount07 : CountPoint {
        :>> mnemonic = "FDR_MON_TRIP_COUNT_07"; :>> pointId = 10055; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount08 : CountPoint {
        :>> mnemonic = "FDR_MON_TRIP_COUNT_08"; :>> pointId = 10056; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount09 : CountPoint {
        :>> mnemonic = "FDR_MON_TRIP_COUNT_09"; :>> pointId = 10057; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount10 : CountPoint {
        :>> mnemonic = "FDR_MON_TRIP_COUNT_10"; :>> pointId = 10058; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount11 : CountPoint {
        :>> mnemonic = "FDR_MON_TRIP_COUNT_11"; :>> pointId = 10059; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount12 : CountPoint {
        :>> mnemonic = "FDR_MON_TRIP_COUNT_12"; :>> pointId = 10060; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount13 : CountPoint {
        :>> mnemonic = "FDR_MON_TRIP_COUNT_13"; :>> pointId = 10061; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount14 : CountPoint {
        :>> mnemonic = "FDR_MON_TRIP_COUNT_14"; :>> pointId = 10062; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount15 : CountPoint {
        :>> mnemonic = "FDR_MON_TRIP_COUNT_15"; :>> pointId = 10063; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount16 : CountPoint {
        :>> mnemonic = "FDR_MON_TRIP_COUNT_16"; :>> pointId = 10064; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount17 : CountPoint {
        :>> mnemonic = "FDR_MON_TRIP_COUNT_17"; :>> pointId = 10065; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount18 : CountPoint {
        :>> mnemonic = "FDR_MON_TRIP_COUNT_18"; :>> pointId = 10066; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount19 : CountPoint {
        :>> mnemonic = "FDR_MON_TRIP_COUNT_19"; :>> pointId = 10067; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount20 : CountPoint {
        :>> mnemonic = "FDR_MON_TRIP_COUNT_20"; :>> pointId = 10068; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount21 : CountPoint {
        :>> mnemonic = "FDR_MON_TRIP_COUNT_21"; :>> pointId = 10069; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount22 : CountPoint {
        :>> mnemonic = "FDR_MON_TRIP_COUNT_22"; :>> pointId = 10070; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount23 : CountPoint {
        :>> mnemonic = "FDR_MON_TRIP_COUNT_23"; :>> pointId = 10071; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount24 : CountPoint {
        :>> mnemonic = "FDR_MON_TRIP_COUNT_24"; :>> pointId = 10072; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount25 : CountPoint {
        :>> mnemonic = "FDR_MON_TRIP_COUNT_25"; :>> pointId = 10073; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount26 : CountPoint {
        :>> mnemonic = "FDR_MON_TRIP_COUNT_26"; :>> pointId = 10074; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount27 : CountPoint {
        :>> mnemonic = "FDR_MON_TRIP_COUNT_27"; :>> pointId = 10075; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount28 : CountPoint {
        :>> mnemonic = "FDR_MON_TRIP_COUNT_28"; :>> pointId = 10076; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount29 : CountPoint {
        :>> mnemonic = "FDR_MON_TRIP_COUNT_29"; :>> pointId = 10077; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount30 : CountPoint {
        :>> mnemonic = "FDR_MON_TRIP_COUNT_30"; :>> pointId = 10078; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount31 : CountPoint {
        :>> mnemonic = "FDR_MON_TRIP_COUNT_31"; :>> pointId = 10079; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount32 : CountPoint {
        :>> mnemonic = "FDR_MON_TRIP_COUNT_32"; :>> pointId = 10080; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount33 : CountPoint {
        :>> mnemonic = "FDR_MON_TRIP_COUNT_33"; :>> pointId = 10081; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount34 : CountPoint {
        :>> mnemonic = "FDR_MON_TRIP_COUNT_34"; :>> pointId = 10082; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount35 : CountPoint {
        :>> mnemonic = "FDR_MON_TRIP_COUNT_35"; :>> pointId = 10083; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount36 : CountPoint {
        :>> mnemonic = "FDR_MON_TRIP_COUNT_36"; :>> pointId = 10084; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount37 : CountPoint {
        :>> mnemonic = "FDR_MON_TRIP_COUNT_37"; :>> pointId = 10085; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount38 : CountPoint {
        :>> mnemonic = "FDR_MON_TRIP_COUNT_38"; :>> pointId = 10086; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount39 : CountPoint {
        :>> mnemonic = "FDR_MON_TRIP_COUNT_39"; :>> pointId = 10087; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount40 : CountPoint {
        :>> mnemonic = "FDR_MON_TRIP_COUNT_40"; :>> pointId = 10088; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount41 : CountPoint {
        :>> mnemonic = "FDR_MON_TRIP_COUNT_41"; :>> pointId = 10089; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount42 : CountPoint {
        :>> mnemonic = "FDR_MON_TRIP_COUNT_42"; :>> pointId = 10090; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount43 : CountPoint {
        :>> mnemonic = "FDR_MON_TRIP_COUNT_43"; :>> pointId = 10091; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount44 : CountPoint {
        :>> mnemonic = "FDR_MON_TRIP_COUNT_44"; :>> pointId = 10092; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount45 : CountPoint {
        :>> mnemonic = "FDR_MON_TRIP_COUNT_45"; :>> pointId = 10093; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount46 : CountPoint {
        :>> mnemonic = "FDR_MON_TRIP_COUNT_46"; :>> pointId = 10094; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount47 : CountPoint {
        :>> mnemonic = "FDR_MON_TRIP_COUNT_47"; :>> pointId = 10095; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrMonTripCount48 : CountPoint {
        :>> mnemonic = "FDR_MON_TRIP_COUNT_48"; :>> pointId = 10096; :>> source = ApplicationName::fdir; :>> apidClass = ApidClass::housekeeping;
        :>> kind = TelemetryKind::engineering; :>> rate = 0.1 [Hz];
        :>> redLow = 0; :>> yellowLow = 0; :>> yellowHigh = 100; :>> redHigh = 1000;
    }
    item fdrFaultCount : CountPoint {
        :>> mnemonic = "FDR_FAULT_COUNT"; :>> pointId = 10097; :>> source = ApplicationName::fdir; :>> apidClass = ApidClass::housekeeping;
        :>> kind = TelemetryKind::housekeeping; :>> rate = 1.0 [Hz];
        :>> redLow = 0; :>> yellowLow = 0; :>> yellowHigh = 10; :>> redHigh = 100;
    }
    item fdrLastFaultId : CountPoint {
        :>> mnemonic = "FDR_LAST_FAULT_ID"; :>> pointId = 10098; :>> source = ApplicationName::fdir; :>> apidClass = ApidClass::housekeeping;
        :>> kind = TelemetryKind::housekeeping; :>> rate = 1.0 [Hz];
        :>> redLow = 0; :>> yellowLow = 0; :>> yellowHigh = 61035 * 65536 + 10240; :>> redHigh = 65535 * 65536 + 65535;
    }
    item fdrSafeModeCount : CountPoint {
        :>> mnemonic = "FDR_SAFE_MODE_COUNT"; :>> pointId = 10099; :>> source = ApplicationName::fdir; :>> apidClass = ApidClass::housekeeping;
        :>> kind = TelemetryKind::housekeeping; :>> rate = 0.1 [Hz];
        :>> redLow = 0; :>> yellowLow = 0; :>> yellowHigh = 2; :>> redHigh = 5;
    }
    item fdrCmdLossTimer : DurationPoint {
        :>> mnemonic = "FDR_CMD_LOSS_TIMER"; :>> pointId = 10100; :>> source = ApplicationName::fdir; :>> apidClass = ApidClass::housekeeping;
        :>> kind = TelemetryKind::housekeeping; :>> rate = 1.0 [Hz];
        :>> redLow = 0.0 [s]; :>> yellowLow = 0.0 [s]; :>> yellowHigh = 518400.0 [s]; :>> redHigh = 604800.0 [s];
    }
    item fdrResponseMask : CountPoint {
        :>> mnemonic = "FDR_RESPONSE_MASK"; :>> pointId = 10101; :>> source = ApplicationName::fdir; :>> apidClass = ApidClass::housekeeping;
        :>> kind = TelemetryKind::housekeeping; :>> rate = 1.0 [Hz];
        :>> redLow = 0; :>> yellowLow = 0; :>> yellowHigh = 61035 * 65536 + 10240; :>> redHigh = 65535 * 65536 + 65535;
    }
    item fdrFlameoutRetries : CountPoint {
        :>> mnemonic = "FDR_FLAMEOUT_RETRIES"; :>> pointId = 10102; :>> source = ApplicationName::fdir; :>> apidClass = ApidClass::housekeeping;
        :>> kind = TelemetryKind::housekeeping; :>> rate = 1.0 [Hz];
        :>> redLow = 0; :>> yellowLow = 0; :>> yellowHigh = 2; :>> redHigh = 2;
    }
    item fdrResponseState : StatusPoint {
        :>> mnemonic = "FDR_RESPONSE_STATE"; :>> pointId = 10103; :>> source = ApplicationName::fdir; :>> apidClass = ApidClass::housekeeping;
        :>> kind = TelemetryKind::housekeeping; :>> rate = 1.0 [Hz];
        :>> redLow = 0; :>> yellowLow = 0; :>> yellowHigh = 254; :>> redHigh = 255;
    }
    item fdrActiveFaults : CountPoint {
        :>> mnemonic = "FDR_ACTIVE_FAULTS"; :>> pointId = 10104; :>> source = ApplicationName::fdir; :>> apidClass = ApidClass::housekeeping;
        :>> kind = TelemetryKind::housekeeping; :>> rate = 1.0 [Hz];
        :>> redLow = 0; :>> yellowLow = 0; :>> yellowHigh = 3; :>> redHigh = 10;
    }
    item fdrImpactProbability : FractionPoint {
        :>> mnemonic = "FDR_IMPACT_PROBABILITY"; :>> pointId = 10105; :>> source = ApplicationName::fdir; :>> apidClass = ApidClass::housekeeping;
        :>> kind = TelemetryKind::housekeeping; :>> rate = 0.1 [Hz];
        :>> redLow = 0.0; :>> yellowLow = 0.0; :>> yellowHigh = 5e-05; :>> redHigh = 0.0001;
    }
    item fdrEarthRange : LengthPoint {
        :>> mnemonic = "FDR_EARTH_RANGE"; :>> pointId = 10106; :>> source = ApplicationName::fdir; :>> apidClass = ApidClass::housekeeping;
        :>> kind = TelemetryKind::housekeeping; :>> rate = 0.1 [Hz];
        :>> redLow = 63781370.0 [m]; :>> yellowLow = 70000000.0 [m]; :>> yellowHigh = 1e+12 [m]; :>> redHigh = 1e+13 [m];
    }
    item modCurrentMode : StatusPoint {
        :>> mnemonic = "MOD_CURRENT_MODE"; :>> pointId = 11001; :>> source = ApplicationName::modeManagement; :>> apidClass = ApidClass::housekeeping;
        :>> kind = TelemetryKind::housekeeping; :>> rate = 1.0 [Hz];
        :>> redLow = 0; :>> yellowLow = 0; :>> yellowHigh = 15; :>> redHigh = 15;
    }
    item modPreviousMode : StatusPoint {
        :>> mnemonic = "MOD_PREVIOUS_MODE"; :>> pointId = 11002; :>> source = ApplicationName::modeManagement; :>> apidClass = ApidClass::housekeeping;
        :>> kind = TelemetryKind::housekeeping; :>> rate = 1.0 [Hz];
        :>> redLow = 0; :>> yellowLow = 0; :>> yellowHigh = 15; :>> redHigh = 15;
    }
    item modModeTime : DurationPoint {
        :>> mnemonic = "MOD_MODE_TIME"; :>> pointId = 11003; :>> source = ApplicationName::modeManagement; :>> apidClass = ApidClass::housekeeping;
        :>> kind = TelemetryKind::housekeeping; :>> rate = 1.0 [Hz];
        :>> redLow = 0.0 [s]; :>> yellowLow = 0.0 [s]; :>> yellowHigh = 10000000.0 [s]; :>> redHigh = 100000000.0 [s];
    }
    item modTransitionCount : CountPoint {
        :>> mnemonic = "MOD_TRANSITION_COUNT"; :>> pointId = 11004; :>> source = ApplicationName::modeManagement; :>> apidClass = ApidClass::housekeeping;
        :>> kind = TelemetryKind::housekeeping; :>> rate = 1.0 [Hz];
        :>> redLow = 0; :>> yellowLow = 0; :>> yellowHigh = 61035 * 65536 + 10240; :>> redHigh = 65535 * 65536 + 65535;
    }
    item modPendingMode : StatusPoint {
        :>> mnemonic = "MOD_PENDING_MODE"; :>> pointId = 11005; :>> source = ApplicationName::modeManagement; :>> apidClass = ApidClass::housekeeping;
        :>> kind = TelemetryKind::housekeeping; :>> rate = 1.0 [Hz];
        :>> redLow = 0; :>> yellowLow = 0; :>> yellowHigh = 15; :>> redHigh = 15;
    }
    item modAutoTransitionEn : StatusPoint {
        :>> mnemonic = "MOD_AUTO_TRANSITION_EN"; :>> pointId = 11006; :>> source = ApplicationName::modeManagement; :>> apidClass = ApidClass::housekeeping;
        :>> kind = TelemetryKind::housekeeping; :>> rate = 1.0 [Hz];
        :>> redLow = 0; :>> yellowLow = 0; :>> yellowHigh = 1; :>> redHigh = 1;
    }
    item modModeTableId : CountPoint {
        :>> mnemonic = "MOD_MODE_TABLE_ID"; :>> pointId = 11007; :>> source = ApplicationName::modeManagement; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item modModeTableCrc : CountPoint {
        :>> mnemonic = "MOD_MODE_TABLE_CRC"; :>> pointId = 11008; :>> source = ApplicationName::modeManagement; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item modSubsystemState01 : StatusPoint {
        :>> mnemonic = "MOD_SUBSYSTEM_STATE_01"; :>> pointId = 11009; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState02 : StatusPoint {
        :>> mnemonic = "MOD_SUBSYSTEM_STATE_02"; :>> pointId = 11010; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState03 : StatusPoint {
        :>> mnemonic = "MOD_SUBSYSTEM_STATE_03"; :>> pointId = 11011; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState04 : StatusPoint {
        :>> mnemonic = "MOD_SUBSYSTEM_STATE_04"; :>> pointId = 11012; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState05 : StatusPoint {
        :>> mnemonic = "MOD_SUBSYSTEM_STATE_05"; :>> pointId = 11013; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState06 : StatusPoint {
        :>> mnemonic = "MOD_SUBSYSTEM_STATE_06"; :>> pointId = 11014; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState07 : StatusPoint {
        :>> mnemonic = "MOD_SUBSYSTEM_STATE_07"; :>> pointId = 11015; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState08 : StatusPoint {
        :>> mnemonic = "MOD_SUBSYSTEM_STATE_08"; :>> pointId = 11016; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState09 : StatusPoint {
        :>> mnemonic = "MOD_SUBSYSTEM_STATE_09"; :>> pointId = 11017; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState10 : StatusPoint {
        :>> mnemonic = "MOD_SUBSYSTEM_STATE_10"; :>> pointId = 11018; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState11 : StatusPoint {
        :>> mnemonic = "MOD_SUBSYSTEM_STATE_11"; :>> pointId = 11019; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modSubsystemState12 : StatusPoint {
        :>> mnemonic = "MOD_SUBSYSTEM_STATE_12"; :>> pointId = 11020; :>> source = ApplicationName::modeManagement; :>> apidClass = ApidClass::housekeeping;
        :>> kind = TelemetryKind::housekeeping; :>> rate = 1.0 [Hz];
        :>> redLow = 0; :>> yellowLow = 0; :>> yellowHigh = 254; :>> redHigh = 255;
    }
    item modModeHold : StatusPoint {
        :>> mnemonic = "MOD_MODE_HOLD"; :>> pointId = 11021; :>> source = ApplicationName::modeManagement; :>> apidClass = ApidClass::housekeeping;
        :>> kind = TelemetryKind::housekeeping; :>> rate = 1.0 [Hz];
        :>> redLow = 0; :>> yellowLow = 0; :>> yellowHigh = 1; :>> redHigh = 1;
    }
    item modTransitionTimeout : DurationPoint {
        :>> mnemonic = "MOD_TRANSITION_TIMEOUT"; :>> pointId = 11022; :>> source = ApplicationName::modeManagement; :>> apidClass = ApidClass::housekeeping;
        :>> kind = TelemetryKind::engineering; :>> rate = 0.1 [Hz];
        :>> redLow = 0.0 [s]; :>> yellowLow = 0.0 [s]; :>> yellowHigh = 10000000.0 [s]; :>> redHigh = 100000000.0 [s];
    }
    item pbuTableId01 : CountPoint {
        :>> mnemonic = "PBU_TABLE_ID_01"; :>> pointId = 12001; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId02 : CountPoint {
        :>> mnemonic = "PBU_TABLE_ID_02"; :>> pointId = 12002; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId03 : CountPoint {
        :>> mnemonic = "PBU_TABLE_ID_03"; :>> pointId = 12003; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId04 : CountPoint {
        :>> mnemonic = "PBU_TABLE_ID_04"; :>> pointId = 12004; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId05 : CountPoint {
        :>> mnemonic = "PBU_TABLE_ID_05"; :>> pointId = 12005; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId06 : CountPoint {
        :>> mnemonic = "PBU_TABLE_ID_06"; :>> pointId = 12006; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId07 : CountPoint {
        :>> mnemonic = "PBU_TABLE_ID_07"; :>> pointId = 12007; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId08 : CountPoint {
        :>> mnemonic = "PBU_TABLE_ID_08"; :>> pointId = 12008; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId09 : CountPoint {
        :>> mnemonic = "PBU_TABLE_ID_09"; :>> pointId = 12009; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId10 : CountPoint {
        :>> mnemonic = "PBU_TABLE_ID_10"; :>> pointId = 12010; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId11 : CountPoint {
        :>> mnemonic = "PBU_TABLE_ID_11"; :>> pointId = 12011; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableId12 : CountPoint {
        :>> mnemonic = "PBU_TABLE_ID_12"; :>> pointId = 12012; :>> source = ApplicationName::parameterBootUpdate; :>> apidClass = ApidClass::housekeeping;
        :>> kind = TelemetryKind::housekeeping; :>> rate = 0.1 [Hz];
        :>> redLow = 0; :>> yellowLow = 0; :>> yellowHigh = 61035 * 65536 + 10240; :>> redHigh = 65535 * 65536 + 65535;
    }
    item pbuTableCrc01 : CountPoint {
        :>> mnemonic = "PBU_TABLE_CRC_01"; :>> pointId = 12013; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc02 : CountPoint {
        :>> mnemonic = "PBU_TABLE_CRC_02"; :>> pointId = 12014; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc03 : CountPoint {
        :>> mnemonic = "PBU_TABLE_CRC_03"; :>> pointId = 12015; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc04 : CountPoint {
        :>> mnemonic = "PBU_TABLE_CRC_04"; :>> pointId = 12016; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc05 : CountPoint {
        :>> mnemonic = "PBU_TABLE_CRC_05"; :>> pointId = 12017; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc06 : CountPoint {
        :>> mnemonic = "PBU_TABLE_CRC_06"; :>> pointId = 12018; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc07 : CountPoint {
        :>> mnemonic = "PBU_TABLE_CRC_07"; :>> pointId = 12019; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc08 : CountPoint {
        :>> mnemonic = "PBU_TABLE_CRC_08"; :>> pointId = 12020; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc09 : CountPoint {
        :>> mnemonic = "PBU_TABLE_CRC_09"; :>> pointId = 12021; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc10 : CountPoint {
        :>> mnemonic = "PBU_TABLE_CRC_10"; :>> pointId = 12022; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc11 : CountPoint {
        :>> mnemonic = "PBU_TABLE_CRC_11"; :>> pointId = 12023; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableCrc12 : CountPoint {
        :>> mnemonic = "PBU_TABLE_CRC_12"; :>> pointId = 12024; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuTableState01 : StatusPoint {
        :>> mnemonic = "PBU_TABLE_STATE_01"; :>> pointId = 12025; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState02 : StatusPoint {
        :>> mnemonic = "PBU_TABLE_STATE_02"; :>> pointId = 12026; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState03 : StatusPoint {
        :>> mnemonic = "PBU_TABLE_STATE_03"; :>> pointId = 12027; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState04 : StatusPoint {
        :>> mnemonic = "PBU_TABLE_STATE_04"; :>> pointId = 12028; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState05 : StatusPoint {
        :>> mnemonic = "PBU_TABLE_STATE_05"; :>> pointId = 12029; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState06 : StatusPoint {
        :>> mnemonic = "PBU_TABLE_STATE_06"; :>> pointId = 12030; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState07 : StatusPoint {
        :>> mnemonic = "PBU_TABLE_STATE_07"; :>> pointId = 12031; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState08 : StatusPoint {
        :>> mnemonic = "PBU_TABLE_STATE_08"; :>> pointId = 12032; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState09 : StatusPoint {
        :>> mnemonic = "PBU_TABLE_STATE_09"; :>> pointId = 12033; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState10 : StatusPoint {
        :>> mnemonic = "PBU_TABLE_STATE_10"; :>> pointId = 12034; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState11 : StatusPoint {
        :>> mnemonic = "PBU_TABLE_STATE_11"; :>> pointId = 12035; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuTableState12 : StatusPoint {
        :>> mnemonic = "PBU_TABLE_STATE_12"; :>> pointId = 12036; :>> source = ApplicationName::parameterBootUpdate; :>> apidClass = ApidClass::housekeeping;
        :>> kind = TelemetryKind::housekeeping; :>> rate = 0.1 [Hz];
        :>> redLow = 0; :>> yellowLow = 0; :>> yellowHigh = 3; :>> redHigh = 3;
    }
    item pbuBootImageSel : StatusPoint {
        :>> mnemonic = "PBU_BOOT_IMAGE_SEL"; :>> pointId = 12037; :>> source = ApplicationName::parameterBootUpdate; :>> apidClass = ApidClass::housekeeping;
        :>> kind = TelemetryKind::housekeeping; :>> rate = 0.1 [Hz];
        :>> redLow = 0; :>> yellowLow = 0; :>> yellowHigh = 1; :>> redHigh = 1;
    }
    item pbuBootImageCrc01 : CountPoint {
        :>> mnemonic = "PBU_BOOT_IMAGE_CRC_01"; :>> pointId = 12038; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuBootImageCrc02 : CountPoint {
        :>> mnemonic = "PBU_BOOT_IMAGE_CRC_02"; :>> pointId = 12039; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuUpdateProgress : FractionPoint {
        :>> mnemonic = "PBU_UPDATE_PROGRESS"; :>> pointId = 12040; :>> source = ApplicationName::parameterBootUpdate; :>> apidClass = ApidClass::housekeeping;
        :>> kind = TelemetryKind::housekeeping; :>> rate = 1.0 [Hz];
        :>> redLow = 0.0; :>> yellowLow = 0.1; :>> yellowHigh = 0.9; :>> redHigh = 1.0;
    }
    item pbuUpdateState : StatusPoint {
        :>> mnemonic = "PBU_UPDATE_STATE"; :>> pointId = 12041; :>> source = ApplicationName::parameterBootUpdate; :>> apidClass = ApidClass::housekeeping;
        :>> kind = TelemetryKind::housekeeping; :>> rate = 1.0 [Hz];
        :>> redLow = 0; :>> yellowLow = 0; :>> yellowHigh = 254; :>> redHigh = 255;
    }
    item pbuParamWriteCount : CountPoint {
        :>> mnemonic = "PBU_PARAM_WRITE_COUNT"; :>> pointId = 12042; :>> source = ApplicationName::parameterBootUpdate; :>> apidClass = ApidClass::housekeeping;
        :>> kind = TelemetryKind::engineering; :>> rate = 0.1 [Hz];
        :>> redLow = 0; :>> yellowLow = 0; :>> yellowHigh = 61035 * 65536 + 10240; :>> redHigh = 65535 * 65536 + 65535;
    }
    item pbuParamRejectCount : CountPoint {
        :>> mnemonic = "PBU_PARAM_REJECT_COUNT"; :>> pointId = 12043; :>> source = ApplicationName::parameterBootUpdate; :>> apidClass = ApidClass::housekeeping;
        :>> kind = TelemetryKind::engineering; :>> rate = 0.1 [Hz];
        :>> redLow = 0; :>> yellowLow = 0; :>> yellowHigh = 10; :>> redHigh = 100;
    }
    item pbuEepromWriteCycles : CountPoint {
        :>> mnemonic = "PBU_EEPROM_WRITE_CYCLES"; :>> pointId = 12044; :>> source = ApplicationName::parameterBootUpdate; :>> apidClass = ApidClass::housekeeping;
        :>> kind = TelemetryKind::engineering; :>> rate = 0.01 [Hz];
        :>> redLow = 0; :>> yellowLow = 0; :>> yellowHigh = 90000; :>> redHigh = 100000;
    }

    // ---- event dictionary: 181 events ----------------------------------------------
    item cdhEvtStarted : EventDefinition {
        :>> eventId = 101; :>> mnemonic = "CDH_EVT_STARTED"; :>> source = ApplicationName::cdh; :>> severity = EventSeverity::info;
        :>> text = "application started"; :>> fdirRelevant = false; :>> isFault = false; :>> level = FdirLevel::unit;
    }
    item cdhEvtStopped : EventDefinition {
        :>> eventId = 102; :>> mnemonic = "CDH_EVT_STOPPED"; :>> source = ApplicationName::cdh; :>> severity = EventSeverity::warning;
        :>> text = "application stopped"; :>> fdirRelevant = false; :>> isFault = false; :>> level = FdirLevel::unit;
    }
    item cdhEvtCmdAccepted : EventDefinition {
        :>> eventId = 103; :>> mnemonic = "CDH_EVT_CMD_ACCEPTED"; :>> source = ApplicationName::cdh; :>> severity = EventSeverity::info;
        :>> text = "command accepted"; :>> fdirRelevant = false; :>> isFault = false; :>> level = FdirLevel::unit;
    }
    item cdhEvtCmdRejected : EventDefinition {
        :>> eventId = 104; :>> mnemonic = "CDH_EVT_CMD_REJECTED"; :>> source = ApplicationName::cdh; :>> severity = EventSeverity::warning;
        :>> text = "command rejected"; :>> fdirRelevant = false; :>> isFault = false; :>> level = FdirLevel::unit;
    }
    item cdhEvtTableLoaded : EventDefinition {
        :>> eventId = 105; :>> mnemonic = "CDH_EVT_TABLE_LOADED"; :>> source = ApplicationName::cdh; :>> severity = EventSeverity::info;
        :>> text = "parameter table loaded"; :>> fdirRelevant = false; :>> isFault = false; :>> level = FdirLevel::unit;
    }
    item cdhEvtTableInvalid : EventDefinition {
        :>> eventId = 106; :>> mnemonic = "CDH_EVT_TABLE_INVALID"; :>> source = ApplicationName::cdh; :>> severity = EventSeverity::fault;
        :>> text = "parameter table failed validation"; :>> fdirRelevant = true; :>> isFault = true; :>> level = FdirLevel::subsystem;
    }
    item cdhEvtWatchdogMissed : EventDefinition {
        :>> eventId = 107; :>> mnemonic = "CDH_EVT_WATCHDOG_MISSED"; :>> source = ApplicationName::cdh; :>> severity = EventSeverity::fault;
        :>> text = "application missed its watchdog window"; :>> fdirRelevant = true; :>> isFault = true; :>> level = FdirLevel::subsystem;
    }
    item cdhEvtModeChangeSeen : EventDefinition {
        :>> eventId = 108; :>> mnemonic = "CDH_EVT_MODE_CHANGE_SEEN"; :>> source = ApplicationName::cdh; :>> severity = EventSeverity::info;
        :>> text = "application applied a mode change"; :>> fdirRelevant = false; :>> isFault = false; :>> level = FdirLevel::unit;
    }
    item cdhEvtProcessorReset : EventDefinition {
        :>> eventId = 109; :>> mnemonic = "CDH_EVT_PROCESSOR_RESET"; :>> source = ApplicationName::cdh; :>> severity = EventSeverity::critical;
        :>> text = "flight computer reset"; :>> fdirRelevant = true; :>> isFault = true; :>> level = FdirLevel::system;
    }
    item cdhEvtPrimeSwitched : EventDefinition {
        :>> eventId = 110; :>> mnemonic = "CDH_EVT_PRIME_SWITCHED"; :>> source = ApplicationName::cdh; :>> severity = EventSeverity::critical;
        :>> text = "prime computer switched"; :>> fdirRelevant = true; :>> isFault = true; :>> level = FdirLevel::system;
    }
    item cdhEvtClockSet : EventDefinition {
        :>> eventId = 111; :>> mnemonic = "CDH_EVT_CLOCK_SET"; :>> source = ApplicationName::cdh; :>> severity = EventSeverity::info;
        :>> text = "spacecraft clock set"; :>> fdirRelevant = false; :>> isFault = false; :>> level = FdirLevel::unit;
    }
    item cdhEvtRecorderFull : EventDefinition {
        :>> eventId = 112; :>> mnemonic = "CDH_EVT_RECORDER_FULL"; :>> source = ApplicationName::cdh; :>> severity = EventSeverity::warning;
        :>> text = "recorder at capacity; oldest files overwritten"; :>> fdirRelevant = false; :>> isFault = false; :>> level = FdirLevel::unit;
    }
    item cdhEvtFileDownlinked : EventDefinition {
        :>> eventId = 113; :>> mnemonic = "CDH_EVT_FILE_DOWNLINKED"; :>> source = ApplicationName::cdh; :>> severity = EventSeverity::info;
        :>> text = "file downlink complete"; :>> fdirRelevant = false; :>> isFault = false; :>> level = FdirLevel::unit;
    }
    item cdhEvtMemoryScrubError : EventDefinition {
        :>> eventId = 114; :>> mnemonic = "CDH_EVT_MEMORY_SCRUB_ERROR"; :>> source = ApplicationName::cdh; :>> severity = EventSeverity::fault;
        :>> text = "uncorrectable memory error scrubbed"; :>> fdirRelevant = true; :>> isFault = true; :>> level = FdirLevel::subsystem;
    }
    item gncEvtStarted : EventDefinition {
        :>> eventId = 201; :>> mnemonic = "GNC_EVT_STARTED"; :>> source = ApplicationName::gnc; :>> severity = EventSeverity::info;
        :>> text = "application started"; :>> fdirRelevant = false; :>> isFault = false; :>> level = FdirLevel::unit;
    }
    item gncEvtStopped : EventDefinition {
        :>> eventId = 202; :>> mnemonic = "GNC_EVT_STOPPED"; :>> source = ApplicationName::gnc; :>> severity = EventSeverity::warning;
        :>> text = "application stopped"; :>> fdirRelevant = false; :>> isFault = false; :>> level = FdirLevel::unit;
    }
    item gncEvtCmdAccepted : EventDefinition {
        :>> eventId = 203; :>> mnemonic = "GNC_EVT_CMD_ACCEPTED"; :>> source = ApplicationName::gnc; :>> severity = EventSeverity::info;
        :>> text = "command accepted"; :>> fdirRelevant = false; :>> isFault = false; :>> level = FdirLevel::unit;
    }
    item gncEvtCmdRejected : EventDefinition {
        :>> eventId = 204; :>> mnemonic = "GNC_EVT_CMD_REJECTED"; :>> source = ApplicationName::gnc; :>> severity = EventSeverity::warning;
        :>> text = "command rejected"; :>> fdirRelevant = false; :>> isFault = false; :>> level = FdirLevel::unit;
    }
    item gncEvtTableLoaded : EventDefinition {
        :>> eventId = 205; :>> mnemonic = "GNC_EVT_TABLE_LOADED"; :>> source = ApplicationName::gnc; :>> severity = EventSeverity::info;
        :>> text = "parameter table loaded"; :>> fdirRelevant = false; :>> isFault = false; :>> level = FdirLevel::unit;
    }
    item gncEvtTableInvalid : EventDefinition {
        :>> eventId = 206; :>> mnemonic = "GNC_EVT_TABLE_INVALID"; :>> source = ApplicationName::gnc; :>> severity = EventSeverity::fault;
        :>> text = "parameter table failed validation"; :>> fdirRelevant = true; :>> isFault = true; :>> level = FdirLevel::subsystem;
    }
    item gncEvtWatchdogMissed : EventDefinition {
        :>> eventId = 207; :>> mnemonic = "GNC_EVT_WATCHDOG_MISSED"; :>> source = ApplicationName::gnc; :>> severity = EventSeverity::fault;
        :>> text = "application missed its watchdog window"; :>> fdirRelevant = true; :>> isFault = true; :>> level = FdirLevel::subsystem;
    }
    item gncEvtModeChangeSeen : EventDefinition {
        :>> eventId = 208; :>> mnemonic = "GNC_EVT_MODE_CHANGE_SEEN"; :>> source = ApplicationName::gnc; :>> severity = EventSeverity::info;
        :>> text = "application applied a mode change"; :>> fdirRelevant = false; :>> isFault = false; :>> level = FdirLevel::unit;
    }
    item gncEvtSlewComplete : EventDefinition {
        :>> eventId = 209; :>> mnemonic = "GNC_EVT_SLEW_COMPLETE"; :>> source = ApplicationName::gnc; :>> severity = EventSeverity::info;
        :>> text = "slew complete within tolerance"; :>> fdirRelevant = false; :>> isFault = false; :>> level = FdirLevel::unit;
    }
    item gncEvtStarTrackerLost : EventDefinition {
        :>> eventId = 210; :>> mnemonic = "GNC_EVT_STAR_TRACKER_LOST"; :>> source = ApplicationName::gnc; :>> severity = EventSeverity::fault;
        :>> text = "star tracker lost lock"; :>> fdirRelevant = true; :>> isFault = true; :>> level = FdirLevel::subsystem;
    }
    item gncEvtImuFault : EventDefinition {
        :>> eventId = 211; :>> mnemonic = "GNC_EVT_IMU_FAULT"; :>> source = ApplicationName::gnc; :>> severity = EventSeverity::fault;
        :>> text = "inertial measurement unit fault"; :>> fdirRelevant = true; :>> isFault = true; :>> level = FdirLevel::subsystem;
    }
    item gncEvtWheelSaturation : EventDefinition {
        :>> eventId = 212; :>> mnemonic = "GNC_EVT_WHEEL_SATURATION"; :>> source = ApplicationName::gnc; :>> severity = EventSeverity::warning;
        :>> text = "reaction wheel near saturation"; :>> fdirRelevant = false; :>> isFault = false; :>> level = FdirLevel::unit;
    }
    item gncEvtDesatComplete : EventDefinition {
        :>> eventId = 213; :>> mnemonic = "GNC_EVT_DESAT_COMPLETE"; :>> source = ApplicationName::gnc; :>> severity = EventSeverity::info;
        :>> text = "momentum dump complete"; :>> fdirRelevant = false; :>> isFault = false; :>> level = FdirLevel::unit;
    }
    item gncEvtTcmComplete : EventDefinition {
        :>> eventId = 214; :>> mnemonic = "GNC_EVT_TCM_COMPLETE"; :>> source = ApplicationName::gnc; :>> severity = EventSeverity::info;
        :>> text = "trajectory correction complete"; :>> fdirRelevant = false; :>> isFault = false; :>> level = FdirLevel::unit;
    }
    item gncEvtEstimatorDiverged : EventDefinition {
        :>> eventId = 215; :>> mnemonic = "GNC_EVT_ESTIMATOR_DIVERGED"; :>> source = ApplicationName::gnc; :>> severity = EventSeverity::critical;
        :>> text = "attitude estimator diverged"; :>> fdirRelevant = true; :>> isFault = true; :>> level = FdirLevel::system;
    }
    item gncEvtEphemerisStale : EventDefinition {
        :>> eventId = 216; :>> mnemonic = "GNC_EVT_EPHEMERIS_STALE"; :>> source = ApplicationName::gnc; :>> severity = EventSeverity::warning;
        :>> text = "ephemeris past validity"; :>> fdirRelevant = false; :>> isFault = false; :>> level = FdirLevel::unit;
    }
    item sepEvtStarted : EventDefinition {
        :>> eventId = 301; :>> mnemonic = "SEP_EVT_STARTED"; :>> source = ApplicationName::sepControl; :>> severity = EventSeverity::info;
        :>> text = "application started"; :>> fdirRelevant = false; :>> isFault = false; :>> level = FdirLevel::unit;
    }
    item sepEvtStopped : EventDefinition {
        :>> eventId = 302; :>> mnemonic = "SEP_EVT_STOPPED"; :>> source = ApplicationName::sepControl; :>> severity = EventSeverity::warning;
        :>> text = "application stopped"; :>> fdirRelevant = false; :>> isFault = false; :>> level = FdirLevel::unit;
    }
    item sepEvtCmdAccepted : EventDefinition {
        :>> eventId = 303; :>> mnemonic = "SEP_EVT_CMD_ACCEPTED"; :>> source = ApplicationName::sepControl; :>> severity = EventSeverity::info;
        :>> text = "command accepted"; :>> fdirRelevant = false; :>> isFault = false; :>> level = FdirLevel::unit;
    }
    item sepEvtCmdRejected : EventDefinition {
        :>> eventId = 304; :>> mnemonic = "SEP_EVT_CMD_REJECTED"; :>> source = ApplicationName::sepControl; :>> severity = EventSeverity::warning;
        :>> text = "command rejected"; :>> fdirRelevant = false; :>> isFault = false; :>> level = FdirLevel::unit;
    }
    item sepEvtTableLoaded : EventDefinition {
        :>> eventId = 305; :>> mnemonic = "SEP_EVT_TABLE_LOADED"; :>> source = ApplicationName::sepControl; :>> severity = EventSeverity::info;
        :>> text = "parameter table loaded"; :>> fdirRelevant = false; :>> isFault = false; :>> level = FdirLevel::unit;
    }
    item sepEvtTableInvalid : EventDefinition {
        :>> eventId = 306; :>> mnemonic = "SEP_EVT_TABLE_INVALID"; :>> source = ApplicationName::sepControl; :>> severity = EventSeverity::fault;
        :>> text = "parameter table failed validation"; :>> fdirRelevant = true; :>> isFault = true; :>> level = FdirLevel::subsystem;
    }
    item sepEvtWatchdogMissed : EventDefinition {
        :>> eventId = 307; :>> mnemonic = "SEP_EVT_WATCHDOG_MISSED"; :>> source = ApplicationName::sepControl; :>> severity = EventSeverity::fault;
        :>> text = "application missed its watchdog window"; :>> fdirRelevant = true; :>> isFault = true; :>> level = FdirLevel::subsystem;
    }
    item sepEvtModeChangeSeen : EventDefinition {
        :>> eventId = 308; :>> mnemonic = "SEP_EVT_MODE_CHANGE_SEEN"; :>> source = ApplicationName::sepControl; :>> severity = EventSeverity::info;
        :>> text = "application applied a mode change"; :>> fdirRelevant = false; :>> isFault = false; :>> level = FdirLevel::unit;
    }
    item sepEvtArcStarted : EventDefinition {
        :>> eventId = 309; :>> mnemonic = "SEP_EVT_ARC_STARTED"; :>> source = ApplicationName::sepControl; :>> severity = EventSeverity::info;
        :>> text = "thrust arc started"; :>> fdirRelevant = false; :>> isFault = false; :>> level = FdirLevel::unit;
    }
    item sepEvtArcComplete : EventDefinition {
        :>> eventId = 310; :>> mnemonic = "SEP_EVT_ARC_COMPLETE"; :>> source = ApplicationName::sepControl; :>> severity = EventSeverity::info;
        :>> text = "thrust arc complete"; :>> fdirRelevant = false; :>> isFault = false; :>> level = FdirLevel::unit;
    }
    item sepEvtFlameout : EventDefinition {
        :>> eventId = 311; :>> mnemonic = "SEP_EVT_FLAMEOUT"; :>> source = ApplicationName::sepControl; :>> severity = EventSeverity::fault;
        :>> text = "thruster flameout"; :>> fdirRelevant = true; :>> isFault = true; :>> level = FdirLevel::subsystem;
    }
    item sepEvtRestartOk : EventDefinition {
        :>> eventId = 312; :>> mnemonic = "SEP_EVT_RESTART_OK"; :>> source = ApplicationName::sepControl; :>> severity = EventSeverity::info;
        :>> text = "thruster restarted"; :>> fdirRelevant = false; :>> isFault = false; :>> level = FdirLevel::unit;
    }
    item sepEvtRestartFailed : EventDefinition {
        :>> eventId = 313; :>> mnemonic = "SEP_EVT_RESTART_FAILED"; :>> source = ApplicationName::sepControl; :>> severity = EventSeverity::critical;
        :>> text = "thruster restart failed; switchover requested"; :>> fdirRelevant = true; :>> isFault = true; :>> level = FdirLevel::system;
    }
    item sepEvtTankLow : EventDefinition {
        :>> eventId = 314; :>> mnemonic = "SEP_EVT_TANK_LOW"; :>> source = ApplicationName::sepControl; :>> severity = EventSeverity::warning;
        :>> text = "xenon below reserve"; :>> fdirRelevant = false; :>> isFault = false; :>> level = FdirLevel::unit;
    }
    item sepEvtPpuOvercurrent : EventDefinition {
        :>> eventId = 315; :>> mnemonic = "SEP_EVT_PPU_OVERCURRENT"; :>> source = ApplicationName::sepControl; :>> severity = EventSeverity::fault;
        :>> text = "power processing unit over-current trip"; :>> fdirRelevant = true; :>> isFault = true; :>> level = FdirLevel::subsystem;
    }
    item sepEvtGimbalStall : EventDefinition {
        :>> eventId = 316; :>> mnemonic = "SEP_EVT_GIMBAL_STALL"; :>> source = ApplicationName::sepControl; :>> severity = EventSeverity::fault;
        :>> text = "gimbal stalled"; :>> fdirRelevant = true; :>> isFault = true; :>> level = FdirLevel::subsystem;
    }
    item epsEvtStarted : EventDefinition {
        :>> eventId = 401; :>> mnemonic = "EPS_EVT_STARTED"; :>> source = ApplicationName::powerManagement; :>> severity = EventSeverity::info;
        :>> text = "application started"; :>> fdirRelevant = false; :>> isFault = false; :>> level = FdirLevel::unit;
    }
    item epsEvtStopped : EventDefinition {
        :>> eventId = 402; :>> mnemonic = "EPS_EVT_STOPPED"; :>> source = ApplicationName::powerManagement; :>> severity = EventSeverity::warning;
        :>> text = "application stopped"; :>> fdirRelevant = false; :>> isFault = false; :>> level = FdirLevel::unit;
    }
    item epsEvtCmdAccepted : EventDefinition {
        :>> eventId = 403; :>> mnemonic = "EPS_EVT_CMD_ACCEPTED"; :>> source = ApplicationName::powerManagement; :>> severity = EventSeverity::info;
        :>> text = "command accepted"; :>> fdirRelevant = false; :>> isFault = false; :>> level = FdirLevel::unit;
    }
    item epsEvtCmdRejected : EventDefinition {
        :>> eventId = 404; :>> mnemonic = "EPS_EVT_CMD_REJECTED"; :>> source = ApplicationName::powerManagement; :>> severity = EventSeverity::warning;
        :>> text = "command rejected"; :>> fdirRelevant = false; :>> isFault = false; :>> level = FdirLevel::unit;
    }
    item epsEvtTableLoaded : EventDefinition {
        :>> eventId = 405; :>> mnemonic = "EPS_EVT_TABLE_LOADED"; :>> source = ApplicationName::powerManagement; :>> severity = EventSeverity::info;
        :>> text = "parameter table loaded"; :>> fdirRelevant = false; :>> isFault = false; :>> level = FdirLevel::unit;
    }
    item epsEvtTableInvalid : EventDefinition {
        :>> eventId = 406; :>> mnemonic = "EPS_EVT_TABLE_INVALID"; :>> source = ApplicationName::powerManagement; :>> severity = EventSeverity::fault;
        :>> text = "parameter table failed validation"; :>> fdirRelevant = true; :>> isFault = true; :>> level = FdirLevel::subsystem;
    }
    item epsEvtWatchdogMissed : EventDefinition {
        :>> eventId = 407; :>> mnemonic = "EPS_EVT_WATCHDOG_MISSED"; :>> source = ApplicationName::powerManagement; :>> severity = EventSeverity::fault;
        :>> text = "application missed its watchdog window"; :>> fdirRelevant = true; :>> isFault = true; :>> level = FdirLevel::subsystem;
    }
    item epsEvtModeChangeSeen : EventDefinition {
        :>> eventId = 408; :>> mnemonic = "EPS_EVT_MODE_CHANGE_SEEN"; :>> source = ApplicationName::powerManagement; :>> severity = EventSeverity::info;
        :>> text = "application applied a mode change"; :>> fdirRelevant = false; :>> isFault = false; :>> level = FdirLevel::unit;
    }
    item epsEvtLoadShed : EventDefinition {
        :>> eventId = 409; :>> mnemonic = "EPS_EVT_LOAD_SHED"; :>> source = ApplicationName::powerManagement; :>> severity = EventSeverity::warning;
        :>> text = "load shed tier applied"; :>> fdirRelevant = false; :>> isFault = false; :>> level = FdirLevel::unit;
    }
    item epsEvtBatteryLow : EventDefinition {
        :>> eventId = 410; :>> mnemonic = "EPS_EVT_BATTERY_LOW"; :>> source = ApplicationName::powerManagement; :>> severity = EventSeverity::fault;
        :>> text = "battery below low fraction"; :>> fdirRelevant = true; :>> isFault = true; :>> level = FdirLevel::subsystem;
    }
    item epsEvtBusUndervoltage : EventDefinition {
        :>> eventId = 411; :>> mnemonic = "EPS_EVT_BUS_UNDERVOLTAGE"; :>> source = ApplicationName::powerManagement; :>> severity = EventSeverity::critical;
        :>> text = "bus under-voltage trip"; :>> fdirRelevant = true; :>> isFault = true; :>> level = FdirLevel::system;
    }
    item epsEvtSwitchTrip : EventDefinition {
        :>> eventId = 412; :>> mnemonic = "EPS_EVT_SWITCH_TRIP"; :>> source = ApplicationName::powerManagement; :>> severity = EventSeverity::fault;
        :>> text = "power switch over-current trip"; :>> fdirRelevant = true; :>> isFault = true; :>> level = FdirLevel::subsystem;
    }
    item epsEvtArrayStringLost : EventDefinition {
        :>> eventId = 413; :>> mnemonic = "EPS_EVT_ARRAY_STRING_LOST"; :>> source = ApplicationName::powerManagement; :>> severity = EventSeverity::warning;
        :>> text = "solar array string open"; :>> fdirRelevant = false; :>> isFault = false; :>> level = FdirLevel::unit;
    }
    item epsEvtSadaStall : EventDefinition {
        :>> eventId = 414; :>> mnemonic = "EPS_EVT_SADA_STALL"; :>> source = ApplicationName::powerManagement; :>> severity = EventSeverity::fault;
        :>> text = "solar array drive stalled"; :>> fdirRelevant = true; :>> isFault = true; :>> level = FdirLevel::subsystem;
    }
    item epsEvtChargeComplete : EventDefinition {
        :>> eventId = 415; :>> mnemonic = "EPS_EVT_CHARGE_COMPLETE"; :>> source = ApplicationName::powerManagement; :>> severity = EventSeverity::info;
        :>> text = "battery charge complete"; :>> fdirRelevant = false; :>> isFault = false; :>> level = FdirLevel::unit;
    }
    item thmEvtStarted : EventDefinition {
        :>> eventId = 501; :>> mnemonic = "THM_EVT_STARTED"; :>> source = ApplicationName::thermalControl; :>> severity = EventSeverity::info;
        :>> text = "application started"; :>> fdirRelevant = false; :>> isFault = false; :>> level = FdirLevel::unit;
    }
    item thmEvtStopped : EventDefinition {
        :>> eventId = 502; :>> mnemonic = "THM_EVT_STOPPED"; :>> source = ApplicationName::thermalControl; :>> severity = EventSeverity::warning;
        :>> text = "application stopped"; :>> fdirRelevant = false; :>> isFault = false; :>> level = FdirLevel::unit;
    }
    item thmEvtCmdAccepted : EventDefinition {
        :>> eventId = 503; :>> mnemonic = "THM_EVT_CMD_ACCEPTED"; :>> source = ApplicationName::thermalControl; :>> severity = EventSeverity::info;
        :>> text = "command accepted"; :>> fdirRelevant = false; :>> isFault = false; :>> level = FdirLevel::unit;
    }
    item thmEvtCmdRejected : EventDefinition {
        :>> eventId = 504; :>> mnemonic = "THM_EVT_CMD_REJECTED"; :>> source = ApplicationName::thermalControl; :>> severity = EventSeverity::warning;
        :>> text = "command rejected"; :>> fdirRelevant = false; :>> isFault = false; :>> level = FdirLevel::unit;
    }
    item thmEvtTableLoaded : EventDefinition {
        :>> eventId = 505; :>> mnemonic = "THM_EVT_TABLE_LOADED"; :>> source = ApplicationName::thermalControl; :>> severity = EventSeverity::info;
        :>> text = "parameter table loaded"; :>> fdirRelevant = false; :>> isFault = false; :>> level = FdirLevel::unit;
    }
    item thmEvtTableInvalid : EventDefinition {
        :>> eventId = 506; :>> mnemonic = "THM_EVT_TABLE_INVALID"; :>> source = ApplicationName::thermalControl; :>> severity = EventSeverity::fault;
        :>> text = "parameter table failed validation"; :>> fdirRelevant = true; :>> isFault = true; :>> level = FdirLevel::subsystem;
    }
    item thmEvtWatchdogMissed : EventDefinition {
        :>> eventId = 507; :>> mnemonic = "THM_EVT_WATCHDOG_MISSED"; :>> source = ApplicationName::thermalControl; :>> severity = EventSeverity::fault;
        :>> text = "application missed its watchdog window"; :>> fdirRelevant = true; :>> isFault = true; :>> level = FdirLevel::subsystem;
    }
    item thmEvtModeChangeSeen : EventDefinition {
        :>> eventId = 508; :>> mnemonic = "THM_EVT_MODE_CHANGE_SEEN"; :>> source = ApplicationName::thermalControl; :>> severity = EventSeverity::info;
        :>> text = "application applied a mode change"; :>> fdirRelevant = false; :>> isFault = false; :>> level = FdirLevel::unit;
    }
    item thmEvtZoneCold : EventDefinition {
        :>> eventId = 509; :>> mnemonic = "THM_EVT_ZONE_COLD"; :>> source = ApplicationName::thermalControl; :>> severity = EventSeverity::warning;
        :>> text = "zone below yellow low"; :>> fdirRelevant = false; :>> isFault = false; :>> level = FdirLevel::unit;
    }
    item thmEvtZoneHot : EventDefinition {
        :>> eventId = 510; :>> mnemonic = "THM_EVT_ZONE_HOT"; :>> source = ApplicationName::thermalControl; :>> severity = EventSeverity::warning;
        :>> text = "zone above yellow high"; :>> fdirRelevant = false; :>> isFault = false; :>> level = FdirLevel::unit;
    }
    item thmEvtZoneRed : EventDefinition {
        :>> eventId = 511; :>> mnemonic = "THM_EVT_ZONE_RED"; :>> source = ApplicationName::thermalControl; :>> severity = EventSeverity::fault;
        :>> text = "zone outside red limits"; :>> fdirRelevant = true; :>> isFault = true; :>> level = FdirLevel::subsystem;
    }
    item thmEvtHeaterFailed : EventDefinition {
        :>> eventId = 512; :>> mnemonic = "THM_EVT_HEATER_FAILED"; :>> source = ApplicationName::thermalControl; :>> severity = EventSeverity::fault;
        :>> text = "heater did not raise its zone"; :>> fdirRelevant = true; :>> isFault = true; :>> level = FdirLevel::subsystem;
    }
    item thmEvtSurvivalActive : EventDefinition {
        :>> eventId = 513; :>> mnemonic = "THM_EVT_SURVIVAL_ACTIVE"; :>> source = ApplicationName::thermalControl; :>> severity = EventSeverity::warning;
        :>> text = "survival heaters active"; :>> fdirRelevant = false; :>> isFault = false; :>> level = FdirLevel::unit;
    }
    item thmEvtPowerCapHit : EventDefinition {
        :>> eventId = 514; :>> mnemonic = "THM_EVT_POWER_CAP_HIT"; :>> source = ApplicationName::thermalControl; :>> severity = EventSeverity::warning;
        :>> text = "heater power cap reached"; :>> fdirRelevant = false; :>> isFault = false; :>> level = FdirLevel::unit;
    }
    item comEvtStarted : EventDefinition {
        :>> eventId = 601; :>> mnemonic = "COM_EVT_STARTED"; :>> source = ApplicationName::telecom; :>> severity = EventSeverity::info;
        :>> text = "application started"; :>> fdirRelevant = false; :>> isFault = false; :>> level = FdirLevel::unit;
    }
    item comEvtStopped : EventDefinition {
        :>> eventId = 602; :>> mnemonic = "COM_EVT_STOPPED"; :>> source = ApplicationName::telecom; :>> severity = EventSeverity::warning;
        :>> text = "application stopped"; :>> fdirRelevant = false; :>> isFault = false; :>> level = FdirLevel::unit;
    }
    item comEvtCmdAccepted : EventDefinition {
        :>> eventId = 603; :>> mnemonic = "COM_EVT_CMD_ACCEPTED"; :>> source = ApplicationName::telecom; :>> severity = EventSeverity::info;
        :>> text = "command accepted"; :>> fdirRelevant = false; :>> isFault = false; :>> level = FdirLevel::unit;
    }
    item comEvtCmdRejected : EventDefinition {
        :>> eventId = 604; :>> mnemonic = "COM_EVT_CMD_REJECTED"; :>> source = ApplicationName::telecom; :>> severity = EventSeverity::warning;
        :>> text = "command rejected"; :>> fdirRelevant = false; :>> isFault = false; :>> level = FdirLevel::unit;
    }
    item comEvtTableLoaded : EventDefinition {
        :>> eventId = 605; :>> mnemonic = "COM_EVT_TABLE_LOADED"; :>> source = ApplicationName::telecom; :>> severity = EventSeverity::info;
        :>> text = "parameter table loaded"; :>> fdirRelevant = false; :>> isFault = false; :>> level = FdirLevel::unit;
    }
    item comEvtTableInvalid : EventDefinition {
        :>> eventId = 606; :>> mnemonic = "COM_EVT_TABLE_INVALID"; :>> source = ApplicationName::telecom; :>> severity = EventSeverity::fault;
        :>> text = "parameter table failed validation"; :>> fdirRelevant = true; :>> isFault = true; :>> level = FdirLevel::subsystem;
    }
    item comEvtWatchdogMissed : EventDefinition {
        :>> eventId = 607; :>> mnemonic = "COM_EVT_WATCHDOG_MISSED"; :>> source = ApplicationName::telecom; :>> severity = EventSeverity::fault;
        :>> text = "application missed its watchdog window"; :>> fdirRelevant = true; :>> isFault = true; :>> level = FdirLevel::subsystem;
    }
    item comEvtModeChangeSeen : EventDefinition {
        :>> eventId = 608; :>> mnemonic = "COM_EVT_MODE_CHANGE_SEEN"; :>> source = ApplicationName::telecom; :>> severity = EventSeverity::info;
        :>> text = "application applied a mode change"; :>> fdirRelevant = false; :>> isFault = false; :>> level = FdirLevel::unit;
    }
    item comEvtCarrierAcquired : EventDefinition {
        :>> eventId = 609; :>> mnemonic = "COM_EVT_CARRIER_ACQUIRED"; :>> source = ApplicationName::telecom; :>> severity = EventSeverity::info;
        :>> text = "uplink carrier acquired"; :>> fdirRelevant = false; :>> isFault = false; :>> level = FdirLevel::unit;
    }
    item comEvtCarrierLost : EventDefinition {
        :>> eventId = 610; :>> mnemonic = "COM_EVT_CARRIER_LOST"; :>> source = ApplicationName::telecom; :>> severity = EventSeverity::warning;
        :>> text = "uplink carrier lost"; :>> fdirRelevant = false; :>> isFault = false; :>> level = FdirLevel::unit;
    }
    item comEvtPassStart : EventDefinition {
        :>> eventId = 611; :>> mnemonic = "COM_EVT_PASS_START"; :>> source = ApplicationName::telecom; :>> severity = EventSeverity::info;
        :>> text = "ground pass started"; :>> fdirRelevant = false; :>> isFault = false; :>> level = FdirLevel::unit;
    }
    item comEvtPassEnd : EventDefinition {
        :>> eventId = 612; :>> mnemonic = "COM_EVT_PASS_END"; :>> source = ApplicationName::telecom; :>> severity = EventSeverity::info;
        :>> text = "ground pass ended"; :>> fdirRelevant = false; :>> isFault = false; :>> level = FdirLevel::unit;
    }
    item comEvtTxOvertemp : EventDefinition {
        :>> eventId = 613; :>> mnemonic = "COM_EVT_TX_OVERTEMP"; :>> source = ApplicationName::telecom; :>> severity = EventSeverity::fault;
        :>> text = "transmitter over temperature"; :>> fdirRelevant = true; :>> isFault = true; :>> level = FdirLevel::subsystem;
    }
    item comEvtHgaPointingError : EventDefinition {
        :>> eventId = 614; :>> mnemonic = "COM_EVT_HGA_POINTING_ERROR"; :>> source = ApplicationName::telecom; :>> severity = EventSeverity::warning;
        :>> text = "high-gain pointing error"; :>> fdirRelevant = false; :>> isFault = false; :>> level = FdirLevel::unit;
    }
    item comEvtRelayAcquired : EventDefinition {
        :>> eventId = 615; :>> mnemonic = "COM_EVT_RELAY_ACQUIRED"; :>> source = ApplicationName::telecom; :>> severity = EventSeverity::info;
        :>> text = "relay link acquired"; :>> fdirRelevant = false; :>> isFault = false; :>> level = FdirLevel::unit;
    }
    item comEvtRelayLost : EventDefinition {
        :>> eventId = 616; :>> mnemonic = "COM_EVT_RELAY_LOST"; :>> source = ApplicationName::telecom; :>> severity = EventSeverity::warning;
        :>> text = "relay link lost"; :>> fdirRelevant = false; :>> isFault = false; :>> level = FdirLevel::unit;
    }
    item insEvtStarted : EventDefinition {
        :>> eventId = 701; :>> mnemonic = "INS_EVT_STARTED"; :>> source = ApplicationName::inspectorHandling; :>> severity = EventSeverity::info;
        :>> text = "application started"; :>> fdirRelevant = false; :>> isFault = false; :>> level = FdirLevel::unit;
    }
    item insEvtStopped : EventDefinition {
        :>> eventId = 702; :>> mnemonic = "INS_EVT_STOPPED"; :>> source = ApplicationName::inspectorHandling; :>> severity = EventSeverity::warning;
        :>> text = "application stopped"; :>> fdirRelevant = false; :>> isFault = false; :>> level = FdirLevel::unit;
    }
    item insEvtCmdAccepted : EventDefinition {
        :>> eventId = 703; :>> mnemonic = "INS_EVT_CMD_ACCEPTED"; :>> source = ApplicationName::inspectorHandling; :>> severity = EventSeverity::info;
        :>> text = "command accepted"; :>> fdirRelevant = false; :>> isFault = false; :>> level = FdirLevel::unit;
    }
    item insEvtCmdRejected : EventDefinition {
        :>> eventId = 704; :>> mnemonic = "INS_EVT_CMD_REJECTED"; :>> source = ApplicationName::inspectorHandling; :>> severity = EventSeverity::warning;
        :>> text = "command rejected"; :>> fdirRelevant = false; :>> isFault = false; :>> level = FdirLevel::unit;
    }
    item insEvtTableLoaded : EventDefinition {
        :>> eventId = 705; :>> mnemonic = "INS_EVT_TABLE_LOADED"; :>> source = ApplicationName::inspectorHandling; :>> severity = EventSeverity::info;
        :>> text = "parameter table loaded"; :>> fdirRelevant = false; :>> isFault = false; :>> level = FdirLevel::unit;
    }
    item insEvtTableInvalid : EventDefinition {
        :>> eventId = 706; :>> mnemonic = "INS_EVT_TABLE_INVALID"; :>> source = ApplicationName::inspectorHandling; :>> severity = EventSeverity::fault;
        :>> text = "parameter table failed validation"; :>> fdirRelevant = true; :>> isFault = true; :>> level = FdirLevel::subsystem;
    }
    item insEvtWatchdogMissed : EventDefinition {
        :>> eventId = 707; :>> mnemonic = "INS_EVT_WATCHDOG_MISSED"; :>> source = ApplicationName::inspectorHandling; :>> severity = EventSeverity::fault;
        :>> text = "application missed its watchdog window"; :>> fdirRelevant = true; :>> isFault = true; :>> level = FdirLevel::subsystem;
    }
    item insEvtModeChangeSeen : EventDefinition {
        :>> eventId = 708; :>> mnemonic = "INS_EVT_MODE_CHANGE_SEEN"; :>> source = ApplicationName::inspectorHandling; :>> severity = EventSeverity::info;
        :>> text = "application applied a mode change"; :>> fdirRelevant = false; :>> isFault = false; :>> level = FdirLevel::unit;
    }
    item insEvtReleaseArmed : EventDefinition {
        :>> eventId = 709; :>> mnemonic = "INS_EVT_RELEASE_ARMED"; :>> source = ApplicationName::inspectorHandling; :>> severity = EventSeverity::warning;
        :>> text = "inspector release armed"; :>> fdirRelevant = false; :>> isFault = false; :>> level = FdirLevel::unit;
    }
    item insEvtReleased : EventDefinition {
        :>> eventId = 710; :>> mnemonic = "INS_EVT_RELEASED"; :>> source = ApplicationName::inspectorHandling; :>> severity = EventSeverity::critical;
        :>> text = "inspector released"; :>> fdirRelevant = true; :>> isFault = true; :>> level = FdirLevel::system;
    }
    item insEvtImageReceived : EventDefinition {
        :>> eventId = 711; :>> mnemonic = "INS_EVT_IMAGE_RECEIVED"; :>> source = ApplicationName::inspectorHandling; :>> severity = EventSeverity::info;
        :>> text = "inspector image complete"; :>> fdirRelevant = false; :>> isFault = false; :>> level = FdirLevel::unit;
    }
    item insEvtSegmentLost : EventDefinition {
        :>> eventId = 712; :>> mnemonic = "INS_EVT_SEGMENT_LOST"; :>> source = ApplicationName::inspectorHandling; :>> severity = EventSeverity::warning;
        :>> text = "image segment lost"; :>> fdirRelevant = false; :>> isFault = false; :>> level = FdirLevel::unit;
    }
    item insEvtInspectorSafe : EventDefinition {
        :>> eventId = 713; :>> mnemonic = "INS_EVT_INSPECTOR_SAFE"; :>> source = ApplicationName::inspectorHandling; :>> severity = EventSeverity::fault;
        :>> text = "inspector reported safe mode"; :>> fdirRelevant = true; :>> isFault = true; :>> level = FdirLevel::subsystem;
    }
    item insEvtInspectorRetired : EventDefinition {
        :>> eventId = 714; :>> mnemonic = "INS_EVT_INSPECTOR_RETIRED"; :>> source = ApplicationName::inspectorHandling; :>> severity = EventSeverity::critical;
        :>> text = "inspector retired"; :>> fdirRelevant = true; :>> isFault = true; :>> level = FdirLevel::system;
    }
    item insEvtContactLost : EventDefinition {
        :>> eventId = 715; :>> mnemonic = "INS_EVT_CONTACT_LOST"; :>> source = ApplicationName::inspectorHandling; :>> severity = EventSeverity::fault;
        :>> text = "inspector contact overdue"; :>> fdirRelevant = true; :>> isFault = true; :>> level = FdirLevel::subsystem;
    }
    item capEvtStarted : EventDefinition {
        :>> eventId = 801; :>> mnemonic = "CAP_EVT_STARTED"; :>> source = ApplicationName::captureControl; :>> severity = EventSeverity::info;
        :>> text = "application started"; :>> fdirRelevant = false; :>> isFault = false; :>> level = FdirLevel::unit;
    }
    item capEvtStopped : EventDefinition {
        :>> eventId = 802; :>> mnemonic = "CAP_EVT_STOPPED"; :>> source = ApplicationName::captureControl; :>> severity = EventSeverity::warning;
        :>> text = "application stopped"; :>> fdirRelevant = false; :>> isFault = false; :>> level = FdirLevel::unit;
    }
    item capEvtCmdAccepted : EventDefinition {
        :>> eventId = 803; :>> mnemonic = "CAP_EVT_CMD_ACCEPTED"; :>> source = ApplicationName::captureControl; :>> severity = EventSeverity::info;
        :>> text = "command accepted"; :>> fdirRelevant = false; :>> isFault = false; :>> level = FdirLevel::unit;
    }
    item capEvtCmdRejected : EventDefinition {
        :>> eventId = 804; :>> mnemonic = "CAP_EVT_CMD_REJECTED"; :>> source = ApplicationName::captureControl; :>> severity = EventSeverity::warning;
        :>> text = "command rejected"; :>> fdirRelevant = false; :>> isFault = false; :>> level = FdirLevel::unit;
    }
    item capEvtTableLoaded : EventDefinition {
        :>> eventId = 805; :>> mnemonic = "CAP_EVT_TABLE_LOADED"; :>> source = ApplicationName::captureControl; :>> severity = EventSeverity::info;
        :>> text = "parameter table loaded"; :>> fdirRelevant = false; :>> isFault = false; :>> level = FdirLevel::unit;
    }
    item capEvtTableInvalid : EventDefinition {
        :>> eventId = 806; :>> mnemonic = "CAP_EVT_TABLE_INVALID"; :>> source = ApplicationName::captureControl; :>> severity = EventSeverity::fault;
        :>> text = "parameter table failed validation"; :>> fdirRelevant = true; :>> isFault = true; :>> level = FdirLevel::subsystem;
    }
    item capEvtWatchdogMissed : EventDefinition {
        :>> eventId = 807; :>> mnemonic = "CAP_EVT_WATCHDOG_MISSED"; :>> source = ApplicationName::captureControl; :>> severity = EventSeverity::fault;
        :>> text = "application missed its watchdog window"; :>> fdirRelevant = true; :>> isFault = true; :>> level = FdirLevel::subsystem;
    }
    item capEvtModeChangeSeen : EventDefinition {
        :>> eventId = 808; :>> mnemonic = "CAP_EVT_MODE_CHANGE_SEEN"; :>> source = ApplicationName::captureControl; :>> severity = EventSeverity::info;
        :>> text = "application applied a mode change"; :>> fdirRelevant = false; :>> isFault = false; :>> level = FdirLevel::unit;
    }
    item capEvtCaptureArmed : EventDefinition {
        :>> eventId = 809; :>> mnemonic = "CAP_EVT_CAPTURE_ARMED"; :>> source = ApplicationName::captureControl; :>> severity = EventSeverity::warning;
        :>> text = "capture armed"; :>> fdirRelevant = false; :>> isFault = false; :>> level = FdirLevel::unit;
    }
    item capEvtBagDeployed : EventDefinition {
        :>> eventId = 810; :>> mnemonic = "CAP_EVT_BAG_DEPLOYED"; :>> source = ApplicationName::captureControl; :>> severity = EventSeverity::critical;
        :>> text = "capture bag deployed"; :>> fdirRelevant = true; :>> isFault = true; :>> level = FdirLevel::system;
    }
    item capEvtBagClosed : EventDefinition {
        :>> eventId = 811; :>> mnemonic = "CAP_EVT_BAG_CLOSED"; :>> source = ApplicationName::captureControl; :>> severity = EventSeverity::critical;
        :>> text = "capture bag closed"; :>> fdirRelevant = true; :>> isFault = true; :>> level = FdirLevel::system;
    }
    item capEvtContact : EventDefinition {
        :>> eventId = 812; :>> mnemonic = "CAP_EVT_CONTACT"; :>> source = ApplicationName::captureControl; :>> severity = EventSeverity::warning;
        :>> text = "body contact detected"; :>> fdirRelevant = false; :>> isFault = false; :>> level = FdirLevel::unit;
    }
    item capEvtContactForceHigh : EventDefinition {
        :>> eventId = 813; :>> mnemonic = "CAP_EVT_CONTACT_FORCE_HIGH"; :>> source = ApplicationName::captureControl; :>> severity = EventSeverity::fault;
        :>> text = "contact force above limit"; :>> fdirRelevant = true; :>> isFault = true; :>> level = FdirLevel::subsystem;
    }
    item capEvtDespinComplete : EventDefinition {
        :>> eventId = 814; :>> mnemonic = "CAP_EVT_DESPIN_COMPLETE"; :>> source = ApplicationName::captureControl; :>> severity = EventSeverity::info;
        :>> text = "despin complete"; :>> fdirRelevant = false; :>> isFault = false; :>> level = FdirLevel::unit;
    }
    item capEvtLatched : EventDefinition {
        :>> eventId = 815; :>> mnemonic = "CAP_EVT_LATCHED"; :>> source = ApplicationName::captureControl; :>> severity = EventSeverity::critical;
        :>> text = "body latched"; :>> fdirRelevant = true; :>> isFault = true; :>> level = FdirLevel::system;
    }
    item capEvtCaptureAborted : EventDefinition {
        :>> eventId = 816; :>> mnemonic = "CAP_EVT_CAPTURE_ABORTED"; :>> source = ApplicationName::captureControl; :>> severity = EventSeverity::critical;
        :>> text = "capture aborted"; :>> fdirRelevant = true; :>> isFault = true; :>> level = FdirLevel::system;
    }
    item capEvtPetalStall : EventDefinition {
        :>> eventId = 817; :>> mnemonic = "CAP_EVT_PETAL_STALL"; :>> source = ApplicationName::captureControl; :>> severity = EventSeverity::fault;
        :>> text = "petal motor stalled"; :>> fdirRelevant = true; :>> isFault = true; :>> level = FdirLevel::subsystem;
    }
    item capEvtProximitySensorFault : EventDefinition {
        :>> eventId = 818; :>> mnemonic = "CAP_EVT_PROXIMITY_SENSOR_FAULT"; :>> source = ApplicationName::captureControl; :>> severity = EventSeverity::fault;
        :>> text = "proximity sensor fault"; :>> fdirRelevant = true; :>> isFault = true; :>> level = FdirLevel::subsystem;
    }
    item autEvtStarted : EventDefinition {
        :>> eventId = 901; :>> mnemonic = "AUT_EVT_STARTED"; :>> source = ApplicationName::autonomy; :>> severity = EventSeverity::info;
        :>> text = "application started"; :>> fdirRelevant = false; :>> isFault = false; :>> level = FdirLevel::unit;
    }
    item autEvtStopped : EventDefinition {
        :>> eventId = 902; :>> mnemonic = "AUT_EVT_STOPPED"; :>> source = ApplicationName::autonomy; :>> severity = EventSeverity::warning;
        :>> text = "application stopped"; :>> fdirRelevant = false; :>> isFault = false; :>> level = FdirLevel::unit;
    }
    item autEvtCmdAccepted : EventDefinition {
        :>> eventId = 903; :>> mnemonic = "AUT_EVT_CMD_ACCEPTED"; :>> source = ApplicationName::autonomy; :>> severity = EventSeverity::info;
        :>> text = "command accepted"; :>> fdirRelevant = false; :>> isFault = false; :>> level = FdirLevel::unit;
    }
    item autEvtCmdRejected : EventDefinition {
        :>> eventId = 904; :>> mnemonic = "AUT_EVT_CMD_REJECTED"; :>> source = ApplicationName::autonomy; :>> severity = EventSeverity::warning;
        :>> text = "command rejected"; :>> fdirRelevant = false; :>> isFault = false; :>> level = FdirLevel::unit;
    }
    item autEvtTableLoaded : EventDefinition {
        :>> eventId = 905; :>> mnemonic = "AUT_EVT_TABLE_LOADED"; :>> source = ApplicationName::autonomy; :>> severity = EventSeverity::info;
        :>> text = "parameter table loaded"; :>> fdirRelevant = false; :>> isFault = false; :>> level = FdirLevel::unit;
    }
    item autEvtTableInvalid : EventDefinition {
        :>> eventId = 906; :>> mnemonic = "AUT_EVT_TABLE_INVALID"; :>> source = ApplicationName::autonomy; :>> severity = EventSeverity::fault;
        :>> text = "parameter table failed validation"; :>> fdirRelevant = true; :>> isFault = true; :>> level = FdirLevel::subsystem;
    }
    item autEvtWatchdogMissed : EventDefinition {
        :>> eventId = 907; :>> mnemonic = "AUT_EVT_WATCHDOG_MISSED"; :>> source = ApplicationName::autonomy; :>> severity = EventSeverity::fault;
        :>> text = "application missed its watchdog window"; :>> fdirRelevant = true; :>> isFault = true; :>> level = FdirLevel::subsystem;
    }
    item autEvtModeChangeSeen : EventDefinition {
        :>> eventId = 908; :>> mnemonic = "AUT_EVT_MODE_CHANGE_SEEN"; :>> source = ApplicationName::autonomy; :>> severity = EventSeverity::info;
        :>> text = "application applied a mode change"; :>> fdirRelevant = false; :>> isFault = false; :>> level = FdirLevel::unit;
    }
    item autEvtSequenceStarted : EventDefinition {
        :>> eventId = 909; :>> mnemonic = "AUT_EVT_SEQUENCE_STARTED"; :>> source = ApplicationName::autonomy; :>> severity = EventSeverity::info;
        :>> text = "sequence started"; :>> fdirRelevant = false; :>> isFault = false; :>> level = FdirLevel::unit;
    }
    item autEvtSequenceComplete : EventDefinition {
        :>> eventId = 910; :>> mnemonic = "AUT_EVT_SEQUENCE_COMPLETE"; :>> source = ApplicationName::autonomy; :>> severity = EventSeverity::info;
        :>> text = "sequence complete"; :>> fdirRelevant = false; :>> isFault = false; :>> level = FdirLevel::unit;
    }
    item autEvtSequenceFailed : EventDefinition {
        :>> eventId = 911; :>> mnemonic = "AUT_EVT_SEQUENCE_FAILED"; :>> source = ApplicationName::autonomy; :>> severity = EventSeverity::fault;
        :>> text = "sequence step failed"; :>> fdirRelevant = true; :>> isFault = true; :>> level = FdirLevel::subsystem;
    }
    item autEvtRuleFired : EventDefinition {
        :>> eventId = 912; :>> mnemonic = "AUT_EVT_RULE_FIRED"; :>> source = ApplicationName::autonomy; :>> severity = EventSeverity::warning;
        :>> text = "autonomy rule fired"; :>> fdirRelevant = false; :>> isFault = false; :>> level = FdirLevel::unit;
    }
    item autEvtWaypointReached : EventDefinition {
        :>> eventId = 913; :>> mnemonic = "AUT_EVT_WAYPOINT_REACHED"; :>> source = ApplicationName::autonomy; :>> severity = EventSeverity::info;
        :>> text = "waypoint reached"; :>> fdirRelevant = false; :>> isFault = false; :>> level = FdirLevel::unit;
    }
    item autEvtPlanInfeasible : EventDefinition {
        :>> eventId = 914; :>> mnemonic = "AUT_EVT_PLAN_INFEASIBLE"; :>> source = ApplicationName::autonomy; :>> severity = EventSeverity::fault;
        :>> text = "plan infeasible within horizon"; :>> fdirRelevant = true; :>> isFault = true; :>> level = FdirLevel::subsystem;
    }
    item fdrEvtStarted : EventDefinition {
        :>> eventId = 1001; :>> mnemonic = "FDR_EVT_STARTED"; :>> source = ApplicationName::fdir; :>> severity = EventSeverity::info;
        :>> text = "application started"; :>> fdirRelevant = false; :>> isFault = false; :>> level = FdirLevel::unit;
    }
    item fdrEvtStopped : EventDefinition {
        :>> eventId = 1002; :>> mnemonic = "FDR_EVT_STOPPED"; :>> source = ApplicationName::fdir; :>> severity = EventSeverity::warning;
        :>> text = "application stopped"; :>> fdirRelevant = false; :>> isFault = false; :>> level = FdirLevel::unit;
    }
    item fdrEvtCmdAccepted : EventDefinition {
        :>> eventId = 1003; :>> mnemonic = "FDR_EVT_CMD_ACCEPTED"; :>> source = ApplicationName::fdir; :>> severity = EventSeverity::info;
        :>> text = "command accepted"; :>> fdirRelevant = false; :>> isFault = false; :>> level = FdirLevel::unit;
    }
    item fdrEvtCmdRejected : EventDefinition {
        :>> eventId = 1004; :>> mnemonic = "FDR_EVT_CMD_REJECTED"; :>> source = ApplicationName::fdir; :>> severity = EventSeverity::warning;
        :>> text = "command rejected"; :>> fdirRelevant = false; :>> isFault = false; :>> level = FdirLevel::unit;
    }
    item fdrEvtTableLoaded : EventDefinition {
        :>> eventId = 1005; :>> mnemonic = "FDR_EVT_TABLE_LOADED"; :>> source = ApplicationName::fdir; :>> severity = EventSeverity::info;
        :>> text = "parameter table loaded"; :>> fdirRelevant = false; :>> isFault = false; :>> level = FdirLevel::unit;
    }
    item fdrEvtTableInvalid : EventDefinition {
        :>> eventId = 1006; :>> mnemonic = "FDR_EVT_TABLE_INVALID"; :>> source = ApplicationName::fdir; :>> severity = EventSeverity::fault;
        :>> text = "parameter table failed validation"; :>> fdirRelevant = true; :>> isFault = true; :>> level = FdirLevel::subsystem;
    }
    item fdrEvtWatchdogMissed : EventDefinition {
        :>> eventId = 1007; :>> mnemonic = "FDR_EVT_WATCHDOG_MISSED"; :>> source = ApplicationName::fdir; :>> severity = EventSeverity::fault;
        :>> text = "application missed its watchdog window"; :>> fdirRelevant = true; :>> isFault = true; :>> level = FdirLevel::subsystem;
    }
    item fdrEvtModeChangeSeen : EventDefinition {
        :>> eventId = 1008; :>> mnemonic = "FDR_EVT_MODE_CHANGE_SEEN"; :>> source = ApplicationName::fdir; :>> severity = EventSeverity::info;
        :>> text = "application applied a mode change"; :>> fdirRelevant = false; :>> isFault = false; :>> level = FdirLevel::unit;
    }
    item fdrEvtMonitorTrip : EventDefinition {
        :>> eventId = 1009; :>> mnemonic = "FDR_EVT_MONITOR_TRIP"; :>> source = ApplicationName::fdir; :>> severity = EventSeverity::fault;
        :>> text = "monitor tripped"; :>> fdirRelevant = true; :>> isFault = true; :>> level = FdirLevel::subsystem;
    }
    item fdrEvtResponseTaken : EventDefinition {
        :>> eventId = 1010; :>> mnemonic = "FDR_EVT_RESPONSE_TAKEN"; :>> source = ApplicationName::fdir; :>> severity = EventSeverity::critical;
        :>> text = "fault response taken"; :>> fdirRelevant = true; :>> isFault = true; :>> level = FdirLevel::system;
    }
    item fdrEvtSafeModeEntered : EventDefinition {
        :>> eventId = 1011; :>> mnemonic = "FDR_EVT_SAFE_MODE_ENTERED"; :>> source = ApplicationName::fdir; :>> severity = EventSeverity::critical;
        :>> text = "safe mode entered"; :>> fdirRelevant = true; :>> isFault = true; :>> level = FdirLevel::system;
    }
    item fdrEvtCommandLoss : EventDefinition {
        :>> eventId = 1012; :>> mnemonic = "FDR_EVT_COMMAND_LOSS"; :>> source = ApplicationName::fdir; :>> severity = EventSeverity::critical;
        :>> text = "command-loss timer expired"; :>> fdirRelevant = true; :>> isFault = true; :>> level = FdirLevel::system;
    }
    item fdrEvtAbortRetreat : EventDefinition {
        :>> eventId = 1013; :>> mnemonic = "FDR_EVT_ABORT_RETREAT"; :>> source = ApplicationName::fdir; :>> severity = EventSeverity::critical;
        :>> text = "abort to retreat commanded"; :>> fdirRelevant = true; :>> isFault = true; :>> level = FdirLevel::system;
    }
    item fdrEvtFaultCleared : EventDefinition {
        :>> eventId = 1014; :>> mnemonic = "FDR_EVT_FAULT_CLEARED"; :>> source = ApplicationName::fdir; :>> severity = EventSeverity::info;
        :>> text = "fault cleared"; :>> fdirRelevant = false; :>> isFault = false; :>> level = FdirLevel::unit;
    }
    item fdrEvtImpactProbabilityHigh : EventDefinition {
        :>> eventId = 1015; :>> mnemonic = "FDR_EVT_IMPACT_PROBABILITY_HIGH"; :>> source = ApplicationName::fdir; :>> severity = EventSeverity::critical;
        :>> text = "Earth impact probability above limit"; :>> fdirRelevant = true; :>> isFault = true; :>> level = FdirLevel::system;
    }
    item fdrEvtExclusionViolation : EventDefinition {
        :>> eventId = 1016; :>> mnemonic = "FDR_EVT_EXCLUSION_VIOLATION"; :>> source = ApplicationName::fdir; :>> severity = EventSeverity::critical;
        :>> text = "trajectory enters Earth exclusion radius"; :>> fdirRelevant = true; :>> isFault = true; :>> level = FdirLevel::system;
    }
    item modEvtStarted : EventDefinition {
        :>> eventId = 1101; :>> mnemonic = "MOD_EVT_STARTED"; :>> source = ApplicationName::modeManagement; :>> severity = EventSeverity::info;
        :>> text = "application started"; :>> fdirRelevant = false; :>> isFault = false; :>> level = FdirLevel::unit;
    }
    item modEvtStopped : EventDefinition {
        :>> eventId = 1102; :>> mnemonic = "MOD_EVT_STOPPED"; :>> source = ApplicationName::modeManagement; :>> severity = EventSeverity::warning;
        :>> text = "application stopped"; :>> fdirRelevant = false; :>> isFault = false; :>> level = FdirLevel::unit;
    }
    item modEvtCmdAccepted : EventDefinition {
        :>> eventId = 1103; :>> mnemonic = "MOD_EVT_CMD_ACCEPTED"; :>> source = ApplicationName::modeManagement; :>> severity = EventSeverity::info;
        :>> text = "command accepted"; :>> fdirRelevant = false; :>> isFault = false; :>> level = FdirLevel::unit;
    }
    item modEvtCmdRejected : EventDefinition {
        :>> eventId = 1104; :>> mnemonic = "MOD_EVT_CMD_REJECTED"; :>> source = ApplicationName::modeManagement; :>> severity = EventSeverity::warning;
        :>> text = "command rejected"; :>> fdirRelevant = false; :>> isFault = false; :>> level = FdirLevel::unit;
    }
    item modEvtTableLoaded : EventDefinition {
        :>> eventId = 1105; :>> mnemonic = "MOD_EVT_TABLE_LOADED"; :>> source = ApplicationName::modeManagement; :>> severity = EventSeverity::info;
        :>> text = "parameter table loaded"; :>> fdirRelevant = false; :>> isFault = false; :>> level = FdirLevel::unit;
    }
    item modEvtTableInvalid : EventDefinition {
        :>> eventId = 1106; :>> mnemonic = "MOD_EVT_TABLE_INVALID"; :>> source = ApplicationName::modeManagement; :>> severity = EventSeverity::fault;
        :>> text = "parameter table failed validation"; :>> fdirRelevant = true; :>> isFault = true; :>> level = FdirLevel::subsystem;
    }
    item modEvtWatchdogMissed : EventDefinition {
        :>> eventId = 1107; :>> mnemonic = "MOD_EVT_WATCHDOG_MISSED"; :>> source = ApplicationName::modeManagement; :>> severity = EventSeverity::fault;
        :>> text = "application missed its watchdog window"; :>> fdirRelevant = true; :>> isFault = true; :>> level = FdirLevel::subsystem;
    }
    item modEvtModeChangeSeen : EventDefinition {
        :>> eventId = 1108; :>> mnemonic = "MOD_EVT_MODE_CHANGE_SEEN"; :>> source = ApplicationName::modeManagement; :>> severity = EventSeverity::info;
        :>> text = "application applied a mode change"; :>> fdirRelevant = false; :>> isFault = false; :>> level = FdirLevel::unit;
    }
    item modEvtModeEntered : EventDefinition {
        :>> eventId = 1109; :>> mnemonic = "MOD_EVT_MODE_ENTERED"; :>> source = ApplicationName::modeManagement; :>> severity = EventSeverity::info;
        :>> text = "mode entered"; :>> fdirRelevant = false; :>> isFault = false; :>> level = FdirLevel::unit;
    }
    item modEvtModePending : EventDefinition {
        :>> eventId = 1110; :>> mnemonic = "MOD_EVT_MODE_PENDING"; :>> source = ApplicationName::modeManagement; :>> severity = EventSeverity::info;
        :>> text = "two-step transition pending"; :>> fdirRelevant = false; :>> isFault = false; :>> level = FdirLevel::unit;
    }
    item modEvtModeRejected : EventDefinition {
        :>> eventId = 1111; :>> mnemonic = "MOD_EVT_MODE_REJECTED"; :>> source = ApplicationName::modeManagement; :>> severity = EventSeverity::warning;
        :>> text = "transition rejected by table"; :>> fdirRelevant = false; :>> isFault = false; :>> level = FdirLevel::unit;
    }
    item modEvtTransitionTimeout : EventDefinition {
        :>> eventId = 1112; :>> mnemonic = "MOD_EVT_TRANSITION_TIMEOUT"; :>> source = ApplicationName::modeManagement; :>> severity = EventSeverity::fault;
        :>> text = "transition did not complete"; :>> fdirRelevant = true; :>> isFault = true; :>> level = FdirLevel::subsystem;
    }
    item modEvtAutoTransition : EventDefinition {
        :>> eventId = 1113; :>> mnemonic = "MOD_EVT_AUTO_TRANSITION"; :>> source = ApplicationName::modeManagement; :>> severity = EventSeverity::warning;
        :>> text = "event-driven transition"; :>> fdirRelevant = false; :>> isFault = false; :>> level = FdirLevel::unit;
    }
    item pbuEvtStarted : EventDefinition {
        :>> eventId = 1201; :>> mnemonic = "PBU_EVT_STARTED"; :>> source = ApplicationName::parameterBootUpdate; :>> severity = EventSeverity::info;
        :>> text = "application started"; :>> fdirRelevant = false; :>> isFault = false; :>> level = FdirLevel::unit;
    }
    item pbuEvtStopped : EventDefinition {
        :>> eventId = 1202; :>> mnemonic = "PBU_EVT_STOPPED"; :>> source = ApplicationName::parameterBootUpdate; :>> severity = EventSeverity::warning;
        :>> text = "application stopped"; :>> fdirRelevant = false; :>> isFault = false; :>> level = FdirLevel::unit;
    }
    item pbuEvtCmdAccepted : EventDefinition {
        :>> eventId = 1203; :>> mnemonic = "PBU_EVT_CMD_ACCEPTED"; :>> source = ApplicationName::parameterBootUpdate; :>> severity = EventSeverity::info;
        :>> text = "command accepted"; :>> fdirRelevant = false; :>> isFault = false; :>> level = FdirLevel::unit;
    }
    item pbuEvtCmdRejected : EventDefinition {
        :>> eventId = 1204; :>> mnemonic = "PBU_EVT_CMD_REJECTED"; :>> source = ApplicationName::parameterBootUpdate; :>> severity = EventSeverity::warning;
        :>> text = "command rejected"; :>> fdirRelevant = false; :>> isFault = false; :>> level = FdirLevel::unit;
    }
    item pbuEvtTableLoaded : EventDefinition {
        :>> eventId = 1205; :>> mnemonic = "PBU_EVT_TABLE_LOADED"; :>> source = ApplicationName::parameterBootUpdate; :>> severity = EventSeverity::info;
        :>> text = "parameter table loaded"; :>> fdirRelevant = false; :>> isFault = false; :>> level = FdirLevel::unit;
    }
    item pbuEvtTableInvalid : EventDefinition {
        :>> eventId = 1206; :>> mnemonic = "PBU_EVT_TABLE_INVALID"; :>> source = ApplicationName::parameterBootUpdate; :>> severity = EventSeverity::fault;
        :>> text = "parameter table failed validation"; :>> fdirRelevant = true; :>> isFault = true; :>> level = FdirLevel::subsystem;
    }
    item pbuEvtWatchdogMissed : EventDefinition {
        :>> eventId = 1207; :>> mnemonic = "PBU_EVT_WATCHDOG_MISSED"; :>> source = ApplicationName::parameterBootUpdate; :>> severity = EventSeverity::fault;
        :>> text = "application missed its watchdog window"; :>> fdirRelevant = true; :>> isFault = true; :>> level = FdirLevel::subsystem;
    }
    item pbuEvtModeChangeSeen : EventDefinition {
        :>> eventId = 1208; :>> mnemonic = "PBU_EVT_MODE_CHANGE_SEEN"; :>> source = ApplicationName::parameterBootUpdate; :>> severity = EventSeverity::info;
        :>> text = "application applied a mode change"; :>> fdirRelevant = false; :>> isFault = false; :>> level = FdirLevel::unit;
    }
    item pbuEvtTableActivated : EventDefinition {
        :>> eventId = 1209; :>> mnemonic = "PBU_EVT_TABLE_ACTIVATED"; :>> source = ApplicationName::parameterBootUpdate; :>> severity = EventSeverity::info;
        :>> text = "table activated"; :>> fdirRelevant = false; :>> isFault = false; :>> level = FdirLevel::unit;
    }
    item pbuEvtTableCrcMismatch : EventDefinition {
        :>> eventId = 1210; :>> mnemonic = "PBU_EVT_TABLE_CRC_MISMATCH"; :>> source = ApplicationName::parameterBootUpdate; :>> severity = EventSeverity::fault;
        :>> text = "table checksum mismatch"; :>> fdirRelevant = true; :>> isFault = true; :>> level = FdirLevel::subsystem;
    }
    item pbuEvtBootUpdateStarted : EventDefinition {
        :>> eventId = 1211; :>> mnemonic = "PBU_EVT_BOOT_UPDATE_STARTED"; :>> source = ApplicationName::parameterBootUpdate; :>> severity = EventSeverity::warning;
        :>> text = "boot image transfer started"; :>> fdirRelevant = false; :>> isFault = false; :>> level = FdirLevel::unit;
    }
    item pbuEvtBootUpdateComplete : EventDefinition {
        :>> eventId = 1212; :>> mnemonic = "PBU_EVT_BOOT_UPDATE_COMPLETE"; :>> source = ApplicationName::parameterBootUpdate; :>> severity = EventSeverity::critical;
        :>> text = "boot image written"; :>> fdirRelevant = true; :>> isFault = true; :>> level = FdirLevel::system;
    }
    item pbuEvtBootFallback : EventDefinition {
        :>> eventId = 1213; :>> mnemonic = "PBU_EVT_BOOT_FALLBACK"; :>> source = ApplicationName::parameterBootUpdate; :>> severity = EventSeverity::critical;
        :>> text = "boot loader fell back to the previous image"; :>> fdirRelevant = true; :>> isFault = true; :>> level = FdirLevel::system;
    }
    item pbuEvtParameterRejected : EventDefinition {
        :>> eventId = 1214; :>> mnemonic = "PBU_EVT_PARAMETER_REJECTED"; :>> source = ApplicationName::parameterBootUpdate; :>> severity = EventSeverity::warning;
        :>> text = "parameter outside its range"; :>> fdirRelevant = false; :>> isFault = false; :>> level = FdirLevel::unit;
    }

    // ---- packet definitions: 51 telemetry packets ---------------------------------
    item cdhHkPacket01 : PacketDefinition {
        :>> packetId = 1; :>> mnemonic = "CDH_HK_01"; :>> apid = 16; :>> apidClass = ApidClass::housekeeping;
        :>> source = ApplicationName::cdh; :>> rate = 1.0 [Hz]; :>> fieldCount = 19; :>> lengthOctets = 58;
        attribute f01 : PacketField { :>> order = 1; :>> offset = 96; :>> width = 16; :>> point = "CDH_T_BOARD_01"; }
        attribute f02 : PacketField { :>> order = 2; :>> offset = 112; :>> width = 16; :>> point = "CDH_T_BOARD_02"; }
        attribute f03 : PacketField { :>> order = 3; :>> offset = 128; :>> width = 16; :>> point = "CDH_T_BOARD_03"; }
        attribute f04 : PacketField { :>> order = 4; :>> offset = 144; :>> width = 16; :>> point = "CDH_T_BOARD_04"; }
        attribute f05 : PacketField { :>> order = 5; :>> offset = 160; :>> width = 16; :>> point = "CDH_CPU_LOAD_01"; }
        attribute f06 : PacketField { :>> order = 6; :>> offset = 176; :>> width = 16; :>> point = "CDH_CPU_LOAD_02"; }
        attribute f07 : PacketField { :>> order = 7; :>> offset = 192; :>> width = 16; :>> point = "CDH_MEM_USED_01"; }
        attribute f08 : PacketField { :>> order = 8; :>> offset = 208; :>> width = 16; :>> point = "CDH_MEM_USED_02"; }
        attribute f09 : PacketField { :>> order = 9; :>> offset = 224; :>> width = 16; :>> point = "CDH_RECORDER_FILL"; }
        attribute f10 : PacketField { :>> order = 10; :>> offset = 240; :>> width = 32; :>> point = "CDH_UPTIME"; }
        attribute f11 : PacketField { :>> order = 11; :>> offset = 272; :>> width = 32; :>> point = "CDH_CMD_ACCEPT_COUNT"; }
        attribute f12 : PacketField { :>> order = 12; :>> offset = 304; :>> width = 32; :>> point = "CDH_CMD_REJECT_COUNT"; }
        attribute f13 : PacketField { :>> order = 13; :>> offset = 336; :>> width = 32; :>> point = "CDH_CLOCK_COARSE"; }
        attribute f14 : PacketField { :>> order = 14; :>> offset = 368; :>> width = 32; :>> point = "CDH_CLOCK_FINE"; }
        attribute f15 : PacketField { :>> order = 15; :>> offset = 400; :>> width = 8; :>> point = "CDH_PARTITION_STATUS_01"; }
        attribute f16 : PacketField { :>> order = 16; :>> offset = 408; :>> width = 8; :>> point = "CDH_PARTITION_STATUS_02"; }
        attribute f17 : PacketField { :>> order = 17; :>> offset = 416; :>> width = 8; :>> point = "CDH_PARTITION_STATUS_03"; }
        attribute f18 : PacketField { :>> order = 18; :>> offset = 424; :>> width = 8; :>> point = "CDH_PARTITION_STATUS_04"; }
        attribute f19 : PacketField { :>> order = 19; :>> offset = 432; :>> width = 32; :>> point = "CDH_WATCHDOG_MARGIN"; }
        :>> widths = (f01.width, f02.width, f03.width, f04.width, f05.width, f06.width, f07.width, f08.width, f09.width, f10.width, f11.width, f12.width, f13.width, f14.width, f15.width, f16.width, f17.width, f18.width, f19.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset);
    }
    item cdhEngPacket01 : PacketDefinition {
        :>> packetId = 2; :>> mnemonic = "CDH_ENG_01"; :>> apid = 17; :>> apidClass = ApidClass::housekeeping;
        :>> source = ApplicationName::cdh; :>> rate = 1.0 [Hz]; :>> fieldCount = 24; :>> lengthOctets = 88;
        attribute f01 : PacketField { :>> order = 1; :>> offset = 96; :>> width = 32; :>> point = "CDH_BUS_MSG_RATE"; }
        attribute f02 : PacketField { :>> order = 2; :>> offset = 128; :>> width = 32; :>> point = "CDH_FILE_COUNT"; }
        attribute f03 : PacketField { :>> order = 3; :>> offset = 160; :>> width = 32; :>> point = "CDH_APP_RATE_01"; }
        attribute f04 : PacketField { :>> order = 4; :>> offset = 192; :>> width = 32; :>> point = "CDH_APP_RATE_02"; }
        attribute f05 : PacketField { :>> order = 5; :>> offset = 224; :>> width = 32; :>> point = "CDH_APP_RATE_03"; }
        attribute f06 : PacketField { :>> order = 6; :>> offset = 256; :>> width = 32; :>> point = "CDH_APP_RATE_04"; }
        attribute f07 : PacketField { :>> order = 7; :>> offset = 288; :>> width = 32; :>> point = "CDH_APP_RATE_05"; }
        attribute f08 : PacketField { :>> order = 8; :>> offset = 320; :>> width = 32; :>> point = "CDH_APP_RATE_06"; }
        attribute f09 : PacketField { :>> order = 9; :>> offset = 352; :>> width = 32; :>> point = "CDH_APP_RATE_07"; }
        attribute f10 : PacketField { :>> order = 10; :>> offset = 384; :>> width = 32; :>> point = "CDH_APP_RATE_08"; }
        attribute f11 : PacketField { :>> order = 11; :>> offset = 416; :>> width = 32; :>> point = "CDH_APP_RATE_09"; }
        attribute f12 : PacketField { :>> order = 12; :>> offset = 448; :>> width = 32; :>> point = "CDH_APP_RATE_10"; }
        attribute f13 : PacketField { :>> order = 13; :>> offset = 480; :>> width = 32; :>> point = "CDH_APP_RATE_11"; }
        attribute f14 : PacketField { :>> order = 14; :>> offset = 512; :>> width = 32; :>> point = "CDH_APP_RATE_12"; }
        attribute f15 : PacketField { :>> order = 15; :>> offset = 544; :>> width = 16; :>> point = "CDH_APP_LOAD_01"; }
        attribute f16 : PacketField { :>> order = 16; :>> offset = 560; :>> width = 16; :>> point = "CDH_APP_LOAD_02"; }
        attribute f17 : PacketField { :>> order = 17; :>> offset = 576; :>> width = 16; :>> point = "CDH_APP_LOAD_03"; }
        attribute f18 : PacketField { :>> order = 18; :>> offset = 592; :>> width = 16; :>> point = "CDH_APP_LOAD_04"; }
        attribute f19 : PacketField { :>> order = 19; :>> offset = 608; :>> width = 16; :>> point = "CDH_APP_LOAD_05"; }
        attribute f20 : PacketField { :>> order = 20; :>> offset = 624; :>> width = 16; :>> point = "CDH_APP_LOAD_06"; }
        attribute f21 : PacketField { :>> order = 21; :>> offset = 640; :>> width = 16; :>> point = "CDH_APP_LOAD_07"; }
        attribute f22 : PacketField { :>> order = 22; :>> offset = 656; :>> width = 16; :>> point = "CDH_APP_LOAD_08"; }
        attribute f23 : PacketField { :>> order = 23; :>> offset = 672; :>> width = 16; :>> point = "CDH_APP_LOAD_09"; }
        attribute f24 : PacketField { :>> order = 24; :>> offset = 688; :>> width = 16; :>> point = "CDH_APP_LOAD_10"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item cdhEngPacket02 : PacketDefinition {
        :>> packetId = 3; :>> mnemonic = "CDH_ENG_02"; :>> apid = 18; :>> apidClass = ApidClass::housekeeping;
        :>> source = ApplicationName::cdh; :>> rate = 0.1 [Hz]; :>> fieldCount = 18; :>> lengthOctets = 80;
        attribute f01 : PacketField { :>> order = 1; :>> offset = 96; :>> width = 16; :>> point = "CDH_APP_LOAD_11"; }
        attribute f02 : PacketField { :>> order = 2; :>> offset = 112; :>> width = 16; :>> point = "CDH_APP_LOAD_12"; }
        attribute f03 : PacketField { :>> order = 3; :>> offset = 128; :>> width = 32; :>> point = "CDH_BUS_RT_ERRORS_01"; }
        attribute f04 : PacketField { :>> order = 4; :>> offset = 160; :>> width = 32; :>> point = "CDH_BUS_RT_ERRORS_02"; }
        attribute f05 : PacketField { :>> order = 5; :>> offset = 192; :>> width = 32; :>> point = "CDH_BUS_RT_ERRORS_03"; }
        attribute f06 : PacketField { :>> order = 6; :>> offset = 224; :>> width = 32; :>> point = "CDH_BUS_RT_ERRORS_04"; }
        attribute f07 : PacketField { :>> order = 7; :>> offset = 256; :>> width = 32; :>> point = "CDH_BUS_RT_ERRORS_05"; }
        attribute f08 : PacketField { :>> order = 8; :>> offset = 288; :>> width = 32; :>> point = "CDH_BUS_RT_ERRORS_06"; }
        attribute f09 : PacketField { :>> order = 9; :>> offset = 320; :>> width = 32; :>> point = "CDH_BUS_RT_ERRORS_07"; }
        attribute f10 : PacketField { :>> order = 10; :>> offset = 352; :>> width = 32; :>> point = "CDH_BUS_RT_ERRORS_08"; }
        attribute f11 : PacketField { :>> order = 11; :>> offset = 384; :>> width = 32; :>> point = "CDH_BUS_RT_ERRORS_09"; }
        attribute f12 : PacketField { :>> order = 12; :>> offset = 416; :>> width = 32; :>> point = "CDH_BUS_RT_ERRORS_10"; }
        attribute f13 : PacketField { :>> order = 13; :>> offset = 448; :>> width = 32; :>> point = "CDH_BUS_RT_ERRORS_11"; }
        attribute f14 : PacketField { :>> order = 14; :>> offset = 480; :>> width = 32; :>> point = "CDH_BUS_RT_ERRORS_12"; }
        attribute f15 : PacketField { :>> order = 15; :>> offset = 512; :>> width = 32; :>> point = "CDH_BUS_RT_ERRORS_13"; }
        attribute f16 : PacketField { :>> order = 16; :>> offset = 544; :>> width = 32; :>> point = "CDH_BUS_RT_ERRORS_14"; }
        attribute f17 : PacketField { :>> order = 17; :>> offset = 576; :>> width = 32; :>> point = "CDH_BUS_RT_ERRORS_15"; }
        attribute f18 : PacketField { :>> order = 18; :>> offset = 608; :>> width = 32; :>> point = "CDH_BUS_RT_ERRORS_16"; }
        :>> widths = (f01.width, f02.width, f03.width, f04.width, f05.width, f06.width, f07.width, f08.width, f09.width, f10.width, f11.width, f12.width, f13.width, f14.width, f15.width, f16.width, f17.width, f18.width);
        :>> offsets = (f01.offset, f02.offset, f03.offset, f04.offset, f05.offset, f06.offset, f07.offset, f08.offset, f09.offset, f10.offset, f11.offset, f12.offset, f13.offset, f14.offset, f15.offset, f16.offset, f17.offset, f18.offset);
    }
    item gncHkPacket01 : PacketDefinition {
        :>> packetId = 4; :>> mnemonic = "GNC_HK_01"; :>> apid = 64; :>> apidClass = ApidClass::guidance;
        :>> source = ApplicationName::gnc; :>> rate = 1.0 [Hz]; :>> fieldCount = 23; :>> lengthOctets = 81;
        attribute f01 : PacketField { :>> order = 1; :>> offset = 96; :>> width = 16; :>> point = "GNC_Q_01"; }
        attribute f02 : PacketField { :>> order = 2; :>> offset = 112; :>> width = 16; :>> point = "GNC_Q_02"; }
        attribute f03 : PacketField { :>> order = 3; :>> offset = 128; :>> width = 16; :>> point = "GNC_Q_03"; }
        attribute f04 : PacketField { :>> order = 4; :>> offset = 144; :>> width = 16; :>> point = "GNC_Q_04"; }
        attribute f05 : PacketField { :>> order = 5; :>> offset = 160; :>> width = 32; :>> point = "GNC_RATE_01"; }
        attribute f06 : PacketField { :>> order = 6; :>> offset = 192; :>> width = 32; :>> point = "GNC_RATE_02"; }
        attribute f07 : PacketField { :>> order = 7; :>> offset = 224; :>> width = 32; :>> point = "GNC_RATE_03"; }
        attribute f08 : PacketField { :>> order = 8; :>> offset = 256; :>> width = 32; :>> point = "GNC_ATT_ERR_01"; }
        attribute f09 : PacketField { :>> order = 9; :>> offset = 288; :>> width = 32; :>> point = "GNC_ATT_ERR_02"; }
        attribute f10 : PacketField { :>> order = 10; :>> offset = 320; :>> width = 32; :>> point = "GNC_ATT_ERR_03"; }
        attribute f11 : PacketField { :>> order = 11; :>> offset = 352; :>> width = 8; :>> point = "GNC_ST_STATUS_01"; }
        attribute f12 : PacketField { :>> order = 12; :>> offset = 360; :>> width = 8; :>> point = "GNC_ST_STATUS_02"; }
        attribute f13 : PacketField { :>> order = 13; :>> offset = 368; :>> width = 32; :>> point = "GNC_WHEEL_SPEED_01"; }
        attribute f14 : PacketField { :>> order = 14; :>> offset = 400; :>> width = 32; :>> point = "GNC_WHEEL_SPEED_02"; }
        attribute f15 : PacketField { :>> order = 15; :>> offset = 432; :>> width = 32; :>> point = "GNC_WHEEL_SPEED_03"; }
        attribute f16 : PacketField { :>> order = 16; :>> offset = 464; :>> width = 32; :>> point = "GNC_WHEEL_SPEED_04"; }
        attribute f17 : PacketField { :>> order = 17; :>> offset = 496; :>> width = 32; :>> point = "GNC_RANGE_TO_TARGET"; }
        attribute f18 : PacketField { :>> order = 18; :>> offset = 528; :>> width = 32; :>> point = "GNC_RANGE_RATE"; }
        attribute f19 : PacketField { :>> order = 19; :>> offset = 560; :>> width = 32; :>> point = "GNC_EPHEMERIS_AGE"; }
        attribute f20 : PacketField { :>> order = 20; :>> offset = 592; :>> width = 8; :>> point = "GNC_GUIDANCE_MODE"; }
        attribute f21 : PacketField { :>> order = 21; :>> offset = 600; :>> width = 16; :>> point = "GNC_MOMENTUM_01"; }
        attribute f22 : PacketField { :>> order = 22; :>> offset = 616; :>> width = 16; :>> point = "GNC_MOMENTUM_02"; }
        attribute f23 : PacketField { :>> order = 23; :>> offset = 632; :>> width = 16; :>> point = "GNC_MOMENTUM_03"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset);
    }
    item gncEngPacket01 : PacketDefinition {
        :>> packetId = 5; :>> mnemonic = "GNC_ENG_01"; :>> apid = 65; :>> apidClass = ApidClass::guidance;
        :>> source = ApplicationName::gnc; :>> rate = 10.0 [Hz]; :>> fieldCount = 24; :>> lengthOctets = 90;
        attribute f01 : PacketField { :>> order = 1; :>> offset = 96; :>> width = 32; :>> point = "GNC_RATE_ERR_01"; }
        attribute f02 : PacketField { :>> order = 2; :>> offset = 128; :>> width = 32; :>> point = "GNC_RATE_ERR_02"; }
        attribute f03 : PacketField { :>> order = 3; :>> offset = 160; :>> width = 32; :>> point = "GNC_RATE_ERR_03"; }
        attribute f04 : PacketField { :>> order = 4; :>> offset = 192; :>> width = 16; :>> point = "GNC_ST_T_01"; }
        attribute f05 : PacketField { :>> order = 5; :>> offset = 208; :>> width = 16; :>> point = "GNC_ST_T_02"; }
        attribute f06 : PacketField { :>> order = 6; :>> offset = 224; :>> width = 32; :>> point = "GNC_IMU_GYRO_01"; }
        attribute f07 : PacketField { :>> order = 7; :>> offset = 256; :>> width = 32; :>> point = "GNC_IMU_GYRO_02"; }
        attribute f08 : PacketField { :>> order = 8; :>> offset = 288; :>> width = 32; :>> point = "GNC_IMU_GYRO_03"; }
        attribute f09 : PacketField { :>> order = 9; :>> offset = 320; :>> width = 32; :>> point = "GNC_IMU_GYRO_04"; }
        attribute f10 : PacketField { :>> order = 10; :>> offset = 352; :>> width = 32; :>> point = "GNC_IMU_GYRO_05"; }
        attribute f11 : PacketField { :>> order = 11; :>> offset = 384; :>> width = 32; :>> point = "GNC_IMU_GYRO_06"; }
        attribute f12 : PacketField { :>> order = 12; :>> offset = 416; :>> width = 32; :>> point = "GNC_IMU_ACCEL_01"; }
        attribute f13 : PacketField { :>> order = 13; :>> offset = 448; :>> width = 32; :>> point = "GNC_IMU_ACCEL_02"; }
        attribute f14 : PacketField { :>> order = 14; :>> offset = 480; :>> width = 32; :>> point = "GNC_IMU_ACCEL_03"; }
        attribute f15 : PacketField { :>> order = 15; :>> offset = 512; :>> width = 32; :>> point = "GNC_IMU_ACCEL_04"; }
        attribute f16 : PacketField { :>> order = 16; :>> offset = 544; :>> width = 32; :>> point = "GNC_IMU_ACCEL_05"; }
        attribute f17 : PacketField { :>> order = 17; :>> offset = 576; :>> width = 32; :>> point = "GNC_IMU_ACCEL_06"; }
        attribute f18 : PacketField { :>> order = 18; :>> offset = 608; :>> width = 16; :>> point = "GNC_IMU_T_01"; }
        attribute f19 : PacketField { :>> order = 19; :>> offset = 624; :>> width = 16; :>> point = "GNC_IMU_T_02"; }
        attribute f20 : PacketField { :>> order = 20; :>> offset = 640; :>> width = 16; :>> point = "GNC_WHEEL_I_01"; }
        attribute f21 : PacketField { :>> order = 21; :>> offset = 656; :>> width = 16; :>> point = "GNC_WHEEL_I_02"; }
        attribute f22 : PacketField { :>> order = 22; :>> offset = 672; :>> width = 16; :>> point = "GNC_WHEEL_I_03"; }
        attribute f23 : PacketField { :>> order = 23; :>> offset = 688; :>> width = 16; :>> point = "GNC_WHEEL_I_04"; }
        attribute f24 : PacketField { :>> order = 24; :>> offset = 704; :>> width = 16; :>> point = "GNC_WHEEL_T_01"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item gncEngPacket02 : PacketDefinition {
        :>> packetId = 6; :>> mnemonic = "GNC_ENG_02"; :>> apid = 66; :>> apidClass = ApidClass::guidance;
        :>> source = ApplicationName::gnc; :>> rate = 1.0 [Hz]; :>> fieldCount = 24; :>> lengthOctets = 92;
        attribute f01 : PacketField { :>> order = 1; :>> offset = 96; :>> width = 16; :>> point = "GNC_WHEEL_T_02"; }
        attribute f02 : PacketField { :>> order = 2; :>> offset = 112; :>> width = 16; :>> point = "GNC_WHEEL_T_03"; }
        attribute f03 : PacketField { :>> order = 3; :>> offset = 128; :>> width = 16; :>> point = "GNC_WHEEL_T_04"; }
        attribute f04 : PacketField { :>> order = 4; :>> offset = 144; :>> width = 32; :>> point = "GNC_RCS_ON_TIME_01"; }
        attribute f05 : PacketField { :>> order = 5; :>> offset = 176; :>> width = 32; :>> point = "GNC_RCS_ON_TIME_02"; }
        attribute f06 : PacketField { :>> order = 6; :>> offset = 208; :>> width = 32; :>> point = "GNC_RCS_ON_TIME_03"; }
        attribute f07 : PacketField { :>> order = 7; :>> offset = 240; :>> width = 32; :>> point = "GNC_RCS_ON_TIME_04"; }
        attribute f08 : PacketField { :>> order = 8; :>> offset = 272; :>> width = 32; :>> point = "GNC_RCS_ON_TIME_05"; }
        attribute f09 : PacketField { :>> order = 9; :>> offset = 304; :>> width = 32; :>> point = "GNC_RCS_ON_TIME_06"; }
        attribute f10 : PacketField { :>> order = 10; :>> offset = 336; :>> width = 32; :>> point = "GNC_RCS_ON_TIME_07"; }
        attribute f11 : PacketField { :>> order = 11; :>> offset = 368; :>> width = 32; :>> point = "GNC_RCS_ON_TIME_08"; }
        attribute f12 : PacketField { :>> order = 12; :>> offset = 400; :>> width = 32; :>> point = "GNC_RCS_PULSES_01"; }
        attribute f13 : PacketField { :>> order = 13; :>> offset = 432; :>> width = 32; :>> point = "GNC_RCS_PULSES_02"; }
        attribute f14 : PacketField { :>> order = 14; :>> offset = 464; :>> width = 32; :>> point = "GNC_RCS_PULSES_03"; }
        attribute f15 : PacketField { :>> order = 15; :>> offset = 496; :>> width = 32; :>> point = "GNC_RCS_PULSES_04"; }
        attribute f16 : PacketField { :>> order = 16; :>> offset = 528; :>> width = 32; :>> point = "GNC_RCS_PULSES_05"; }
        attribute f17 : PacketField { :>> order = 17; :>> offset = 560; :>> width = 32; :>> point = "GNC_RCS_PULSES_06"; }
        attribute f18 : PacketField { :>> order = 18; :>> offset = 592; :>> width = 32; :>> point = "GNC_RCS_PULSES_07"; }
        attribute f19 : PacketField { :>> order = 19; :>> offset = 624; :>> width = 32; :>> point = "GNC_RCS_PULSES_08"; }
        attribute f20 : PacketField { :>> order = 20; :>> offset = 656; :>> width = 16; :>> point = "GNC_SUN_SENSOR_01"; }
        attribute f21 : PacketField { :>> order = 21; :>> offset = 672; :>> width = 16; :>> point = "GNC_SUN_SENSOR_02"; }
        attribute f22 : PacketField { :>> order = 22; :>> offset = 688; :>> width = 16; :>> point = "GNC_SUN_SENSOR_03"; }
        attribute f23 : PacketField { :>> order = 23; :>> offset = 704; :>> width = 16; :>> point = "GNC_SUN_SENSOR_04"; }
        attribute f24 : PacketField { :>> order = 24; :>> offset = 720; :>> width = 16; :>> point = "GNC_SUN_SENSOR_05"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item gncEngPacket03 : PacketDefinition {
        :>> packetId = 7; :>> mnemonic = "GNC_ENG_03"; :>> apid = 67; :>> apidClass = ApidClass::guidance;
        :>> source = ApplicationName::gnc; :>> rate = 1.0 [Hz]; :>> fieldCount = 3; :>> lengthOctets = 22;
        attribute f01 : PacketField { :>> order = 1; :>> offset = 96; :>> width = 16; :>> point = "GNC_SUN_SENSOR_06"; }
        attribute f02 : PacketField { :>> order = 2; :>> offset = 112; :>> width = 32; :>> point = "GNC_BEARING_01"; }
        attribute f03 : PacketField { :>> order = 3; :>> offset = 144; :>> width = 32; :>> point = "GNC_BEARING_02"; }
        :>> widths = (f01.width, f02.width, f03.width);
        :>> offsets = (f01.offset, f02.offset, f03.offset);
    }
    item sepHkPacket01 : PacketDefinition {
        :>> packetId = 8; :>> mnemonic = "SEP_HK_01"; :>> apid = 128; :>> apidClass = ApidClass::propulsion;
        :>> source = ApplicationName::sepControl; :>> rate = 1.0 [Hz]; :>> fieldCount = 24; :>> lengthOctets = 54;
        attribute f01 : PacketField { :>> order = 1; :>> offset = 96; :>> width = 16; :>> point = "SEP_DISCHARGE_I_01"; }
        attribute f02 : PacketField { :>> order = 2; :>> offset = 112; :>> width = 16; :>> point = "SEP_DISCHARGE_I_02"; }
        attribute f03 : PacketField { :>> order = 3; :>> offset = 128; :>> width = 16; :>> point = "SEP_DISCHARGE_I_03"; }
        attribute f04 : PacketField { :>> order = 4; :>> offset = 144; :>> width = 16; :>> point = "SEP_DISCHARGE_V_01"; }
        attribute f05 : PacketField { :>> order = 5; :>> offset = 160; :>> width = 16; :>> point = "SEP_DISCHARGE_V_02"; }
        attribute f06 : PacketField { :>> order = 6; :>> offset = 176; :>> width = 16; :>> point = "SEP_DISCHARGE_V_03"; }
        attribute f07 : PacketField { :>> order = 7; :>> offset = 192; :>> width = 16; :>> point = "SEP_PPU_IN_POWER_01"; }
        attribute f08 : PacketField { :>> order = 8; :>> offset = 208; :>> width = 16; :>> point = "SEP_PPU_IN_POWER_02"; }
        attribute f09 : PacketField { :>> order = 9; :>> offset = 224; :>> width = 16; :>> point = "SEP_PPU_IN_POWER_03"; }
        attribute f10 : PacketField { :>> order = 10; :>> offset = 240; :>> width = 8; :>> point = "SEP_PPU_STATUS_01"; }
        attribute f11 : PacketField { :>> order = 11; :>> offset = 248; :>> width = 8; :>> point = "SEP_PPU_STATUS_02"; }
        attribute f12 : PacketField { :>> order = 12; :>> offset = 256; :>> width = 8; :>> point = "SEP_PPU_STATUS_03"; }
        attribute f13 : PacketField { :>> order = 13; :>> offset = 264; :>> width = 16; :>> point = "SEP_TANK_P_01"; }
        attribute f14 : PacketField { :>> order = 14; :>> offset = 280; :>> width = 16; :>> point = "SEP_TANK_P_02"; }
        attribute f15 : PacketField { :>> order = 15; :>> offset = 296; :>> width = 16; :>> point = "SEP_TANK_T_01"; }
        attribute f16 : PacketField { :>> order = 16; :>> offset = 312; :>> width = 16; :>> point = "SEP_TANK_T_02"; }
        attribute f17 : PacketField { :>> order = 17; :>> offset = 328; :>> width = 32; :>> point = "SEP_XENON_REMAINING"; }
        attribute f18 : PacketField { :>> order = 18; :>> offset = 360; :>> width = 16; :>> point = "SEP_REG_P_01"; }
        attribute f19 : PacketField { :>> order = 19; :>> offset = 376; :>> width = 16; :>> point = "SEP_REG_P_02"; }
        attribute f20 : PacketField { :>> order = 20; :>> offset = 392; :>> width = 8; :>> point = "SEP_LATCH_VALVE_01"; }
        attribute f21 : PacketField { :>> order = 21; :>> offset = 400; :>> width = 8; :>> point = "SEP_LATCH_VALVE_02"; }
        attribute f22 : PacketField { :>> order = 22; :>> offset = 408; :>> width = 8; :>> point = "SEP_LATCH_VALVE_03"; }
        attribute f23 : PacketField { :>> order = 23; :>> offset = 416; :>> width = 8; :>> point = "SEP_LATCH_VALVE_04"; }
        attribute f24 : PacketField { :>> order = 24; :>> offset = 424; :>> width = 8; :>> point = "SEP_LATCH_VALVE_05"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item sepHkPacket02 : PacketDefinition {
        :>> packetId = 9; :>> mnemonic = "SEP_HK_02"; :>> apid = 129; :>> apidClass = ApidClass::propulsion;
        :>> source = ApplicationName::sepControl; :>> rate = 1.0 [Hz]; :>> fieldCount = 4; :>> lengthOctets = 23;
        attribute f01 : PacketField { :>> order = 1; :>> offset = 96; :>> width = 8; :>> point = "SEP_LATCH_VALVE_06"; }
        attribute f02 : PacketField { :>> order = 2; :>> offset = 104; :>> width = 16; :>> point = "SEP_THRUST_EST"; }
        attribute f03 : PacketField { :>> order = 3; :>> offset = 120; :>> width = 32; :>> point = "SEP_ARC_ELAPSED"; }
        attribute f04 : PacketField { :>> order = 4; :>> offset = 152; :>> width = 32; :>> point = "SEP_ARC_REMAINING"; }
        :>> widths = (f01.width, f02.width, f03.width, f04.width);
        :>> offsets = (f01.offset, f02.offset, f03.offset, f04.offset);
    }
    item sepEngPacket01 : PacketDefinition {
        :>> packetId = 10; :>> mnemonic = "SEP_ENG_01"; :>> apid = 130; :>> apidClass = ApidClass::propulsion;
        :>> source = ApplicationName::sepControl; :>> rate = 1.0 [Hz]; :>> fieldCount = 24; :>> lengthOctets = 60;
        attribute f01 : PacketField { :>> order = 1; :>> offset = 96; :>> width = 16; :>> point = "SEP_ANODE_FLOW_01"; }
        attribute f02 : PacketField { :>> order = 2; :>> offset = 112; :>> width = 16; :>> point = "SEP_ANODE_FLOW_02"; }
        attribute f03 : PacketField { :>> order = 3; :>> offset = 128; :>> width = 16; :>> point = "SEP_ANODE_FLOW_03"; }
        attribute f04 : PacketField { :>> order = 4; :>> offset = 144; :>> width = 16; :>> point = "SEP_CATHODE_FLOW_01"; }
        attribute f05 : PacketField { :>> order = 5; :>> offset = 160; :>> width = 16; :>> point = "SEP_CATHODE_FLOW_02"; }
        attribute f06 : PacketField { :>> order = 6; :>> offset = 176; :>> width = 16; :>> point = "SEP_CATHODE_FLOW_03"; }
        attribute f07 : PacketField { :>> order = 7; :>> offset = 192; :>> width = 16; :>> point = "SEP_KEEPER_I_01"; }
        attribute f08 : PacketField { :>> order = 8; :>> offset = 208; :>> width = 16; :>> point = "SEP_KEEPER_I_02"; }
        attribute f09 : PacketField { :>> order = 9; :>> offset = 224; :>> width = 16; :>> point = "SEP_KEEPER_I_03"; }
        attribute f10 : PacketField { :>> order = 10; :>> offset = 240; :>> width = 16; :>> point = "SEP_MAGNET_I_01"; }
        attribute f11 : PacketField { :>> order = 11; :>> offset = 256; :>> width = 16; :>> point = "SEP_MAGNET_I_02"; }
        attribute f12 : PacketField { :>> order = 12; :>> offset = 272; :>> width = 16; :>> point = "SEP_MAGNET_I_03"; }
        attribute f13 : PacketField { :>> order = 13; :>> offset = 288; :>> width = 16; :>> point = "SEP_CATHODE_HTR_I_01"; }
        attribute f14 : PacketField { :>> order = 14; :>> offset = 304; :>> width = 16; :>> point = "SEP_CATHODE_HTR_I_02"; }
        attribute f15 : PacketField { :>> order = 15; :>> offset = 320; :>> width = 16; :>> point = "SEP_CATHODE_HTR_I_03"; }
        attribute f16 : PacketField { :>> order = 16; :>> offset = 336; :>> width = 16; :>> point = "SEP_THRUSTER_T_01"; }
        attribute f17 : PacketField { :>> order = 17; :>> offset = 352; :>> width = 16; :>> point = "SEP_THRUSTER_T_02"; }
        attribute f18 : PacketField { :>> order = 18; :>> offset = 368; :>> width = 16; :>> point = "SEP_THRUSTER_T_03"; }
        attribute f19 : PacketField { :>> order = 19; :>> offset = 384; :>> width = 16; :>> point = "SEP_PPU_T_01"; }
        attribute f20 : PacketField { :>> order = 20; :>> offset = 400; :>> width = 16; :>> point = "SEP_PPU_T_02"; }
        attribute f21 : PacketField { :>> order = 21; :>> offset = 416; :>> width = 16; :>> point = "SEP_PPU_T_03"; }
        attribute f22 : PacketField { :>> order = 22; :>> offset = 432; :>> width = 16; :>> point = "SEP_PPU_EFFICIENCY_01"; }
        attribute f23 : PacketField { :>> order = 23; :>> offset = 448; :>> width = 16; :>> point = "SEP_PPU_EFFICIENCY_02"; }
        attribute f24 : PacketField { :>> order = 24; :>> offset = 464; :>> width = 16; :>> point = "SEP_PPU_EFFICIENCY_03"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item sepEngPacket02 : PacketDefinition {
        :>> packetId = 11; :>> mnemonic = "SEP_ENG_02"; :>> apid = 131; :>> apidClass = ApidClass::propulsion;
        :>> source = ApplicationName::sepControl; :>> rate = 1.0 [Hz]; :>> fieldCount = 8; :>> lengthOctets = 44;
        attribute f01 : PacketField { :>> order = 1; :>> offset = 96; :>> width = 32; :>> point = "SEP_FLOW_TOTAL"; }
        attribute f02 : PacketField { :>> order = 2; :>> offset = 128; :>> width = 32; :>> point = "SEP_GIMBAL_ANGLE_01"; }
        attribute f03 : PacketField { :>> order = 3; :>> offset = 160; :>> width = 32; :>> point = "SEP_GIMBAL_ANGLE_02"; }
        attribute f04 : PacketField { :>> order = 4; :>> offset = 192; :>> width = 32; :>> point = "SEP_GIMBAL_ANGLE_03"; }
        attribute f05 : PacketField { :>> order = 5; :>> offset = 224; :>> width = 32; :>> point = "SEP_GIMBAL_ANGLE_04"; }
        attribute f06 : PacketField { :>> order = 6; :>> offset = 256; :>> width = 32; :>> point = "SEP_GIMBAL_ANGLE_05"; }
        attribute f07 : PacketField { :>> order = 7; :>> offset = 288; :>> width = 32; :>> point = "SEP_GIMBAL_ANGLE_06"; }
        attribute f08 : PacketField { :>> order = 8; :>> offset = 320; :>> width = 32; :>> point = "SEP_ISP_EST"; }
        :>> widths = (f01.width, f02.width, f03.width, f04.width, f05.width, f06.width, f07.width, f08.width);
        :>> offsets = (f01.offset, f02.offset, f03.offset, f04.offset, f05.offset, f06.offset, f07.offset, f08.offset);
    }
    item epsHkPacket01 : PacketDefinition {
        :>> packetId = 12; :>> mnemonic = "EPS_HK_01"; :>> apid = 19; :>> apidClass = ApidClass::housekeeping;
        :>> source = ApplicationName::powerManagement; :>> rate = 1.0 [Hz]; :>> fieldCount = 24; :>> lengthOctets = 52;
        attribute f01 : PacketField { :>> order = 1; :>> offset = 96; :>> width = 16; :>> point = "EPS_BATT_T_01"; }
        attribute f02 : PacketField { :>> order = 2; :>> offset = 112; :>> width = 16; :>> point = "EPS_BATT_T_02"; }
        attribute f03 : PacketField { :>> order = 3; :>> offset = 128; :>> width = 16; :>> point = "EPS_BATT_T_03"; }
        attribute f04 : PacketField { :>> order = 4; :>> offset = 144; :>> width = 16; :>> point = "EPS_BATT_T_04"; }
        attribute f05 : PacketField { :>> order = 5; :>> offset = 160; :>> width = 16; :>> point = "EPS_BATT_SOC_01"; }
        attribute f06 : PacketField { :>> order = 6; :>> offset = 176; :>> width = 16; :>> point = "EPS_BATT_SOC_02"; }
        attribute f07 : PacketField { :>> order = 7; :>> offset = 192; :>> width = 16; :>> point = "EPS_BATT_I_01"; }
        attribute f08 : PacketField { :>> order = 8; :>> offset = 208; :>> width = 16; :>> point = "EPS_BATT_I_02"; }
        attribute f09 : PacketField { :>> order = 9; :>> offset = 224; :>> width = 16; :>> point = "EPS_ARRAY_V_01"; }
        attribute f10 : PacketField { :>> order = 10; :>> offset = 240; :>> width = 16; :>> point = "EPS_ARRAY_V_02"; }
        attribute f11 : PacketField { :>> order = 11; :>> offset = 256; :>> width = 16; :>> point = "EPS_ARRAY_V_03"; }
        attribute f12 : PacketField { :>> order = 12; :>> offset = 272; :>> width = 16; :>> point = "EPS_ARRAY_V_04"; }
        attribute f13 : PacketField { :>> order = 13; :>> offset = 288; :>> width = 16; :>> point = "EPS_BUS_V_01"; }
        attribute f14 : PacketField { :>> order = 14; :>> offset = 304; :>> width = 16; :>> point = "EPS_BUS_V_02"; }
        attribute f15 : PacketField { :>> order = 15; :>> offset = 320; :>> width = 16; :>> point = "EPS_BUS_I_01"; }
        attribute f16 : PacketField { :>> order = 16; :>> offset = 336; :>> width = 16; :>> point = "EPS_BUS_I_02"; }
        attribute f17 : PacketField { :>> order = 17; :>> offset = 352; :>> width = 8; :>> point = "EPS_SW_STATE_01"; }
        attribute f18 : PacketField { :>> order = 18; :>> offset = 360; :>> width = 8; :>> point = "EPS_SW_STATE_02"; }
        attribute f19 : PacketField { :>> order = 19; :>> offset = 368; :>> width = 8; :>> point = "EPS_SW_STATE_03"; }
        attribute f20 : PacketField { :>> order = 20; :>> offset = 376; :>> width = 8; :>> point = "EPS_SW_STATE_04"; }
        attribute f21 : PacketField { :>> order = 21; :>> offset = 384; :>> width = 8; :>> point = "EPS_SW_STATE_05"; }
        attribute f22 : PacketField { :>> order = 22; :>> offset = 392; :>> width = 8; :>> point = "EPS_SW_STATE_06"; }
        attribute f23 : PacketField { :>> order = 23; :>> offset = 400; :>> width = 8; :>> point = "EPS_SW_STATE_07"; }
        attribute f24 : PacketField { :>> order = 24; :>> offset = 408; :>> width = 8; :>> point = "EPS_SW_STATE_08"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item epsHkPacket02 : PacketDefinition {
        :>> packetId = 13; :>> mnemonic = "EPS_HK_02"; :>> apid = 20; :>> apidClass = ApidClass::housekeeping;
        :>> source = ApplicationName::powerManagement; :>> rate = 1.0 [Hz]; :>> fieldCount = 23; :>> lengthOctets = 45;
        attribute f01 : PacketField { :>> order = 1; :>> offset = 96; :>> width = 8; :>> point = "EPS_SW_STATE_09"; }
        attribute f02 : PacketField { :>> order = 2; :>> offset = 104; :>> width = 8; :>> point = "EPS_SW_STATE_10"; }
        attribute f03 : PacketField { :>> order = 3; :>> offset = 112; :>> width = 8; :>> point = "EPS_SW_STATE_11"; }
        attribute f04 : PacketField { :>> order = 4; :>> offset = 120; :>> width = 8; :>> point = "EPS_SW_STATE_12"; }
        attribute f05 : PacketField { :>> order = 5; :>> offset = 128; :>> width = 8; :>> point = "EPS_SW_STATE_13"; }
        attribute f06 : PacketField { :>> order = 6; :>> offset = 136; :>> width = 8; :>> point = "EPS_SW_STATE_14"; }
        attribute f07 : PacketField { :>> order = 7; :>> offset = 144; :>> width = 8; :>> point = "EPS_SW_STATE_15"; }
        attribute f08 : PacketField { :>> order = 8; :>> offset = 152; :>> width = 8; :>> point = "EPS_SW_STATE_16"; }
        attribute f09 : PacketField { :>> order = 9; :>> offset = 160; :>> width = 8; :>> point = "EPS_SW_STATE_17"; }
        attribute f10 : PacketField { :>> order = 10; :>> offset = 168; :>> width = 8; :>> point = "EPS_SW_STATE_18"; }
        attribute f11 : PacketField { :>> order = 11; :>> offset = 176; :>> width = 8; :>> point = "EPS_SW_STATE_19"; }
        attribute f12 : PacketField { :>> order = 12; :>> offset = 184; :>> width = 8; :>> point = "EPS_SW_STATE_20"; }
        attribute f13 : PacketField { :>> order = 13; :>> offset = 192; :>> width = 8; :>> point = "EPS_SW_STATE_21"; }
        attribute f14 : PacketField { :>> order = 14; :>> offset = 200; :>> width = 8; :>> point = "EPS_SW_STATE_22"; }
        attribute f15 : PacketField { :>> order = 15; :>> offset = 208; :>> width = 8; :>> point = "EPS_SW_STATE_23"; }
        attribute f16 : PacketField { :>> order = 16; :>> offset = 216; :>> width = 8; :>> point = "EPS_SW_STATE_24"; }
        attribute f17 : PacketField { :>> order = 17; :>> offset = 224; :>> width = 32; :>> point = "EPS_SADA_ANGLE_01"; }
        attribute f18 : PacketField { :>> order = 18; :>> offset = 256; :>> width = 32; :>> point = "EPS_SADA_ANGLE_02"; }
        attribute f19 : PacketField { :>> order = 19; :>> offset = 288; :>> width = 16; :>> point = "EPS_PCU_T_01"; }
        attribute f20 : PacketField { :>> order = 20; :>> offset = 304; :>> width = 16; :>> point = "EPS_PCU_T_02"; }
        attribute f21 : PacketField { :>> order = 21; :>> offset = 320; :>> width = 8; :>> point = "EPS_LOAD_SHED_LEVEL"; }
        attribute f22 : PacketField { :>> order = 22; :>> offset = 328; :>> width = 16; :>> point = "EPS_TOTAL_LOAD"; }
        attribute f23 : PacketField { :>> order = 23; :>> offset = 344; :>> width = 16; :>> point = "EPS_ARRAY_POWER"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset);
    }
    item epsEngPacket01 : PacketDefinition {
        :>> packetId = 14; :>> mnemonic = "EPS_ENG_01"; :>> apid = 21; :>> apidClass = ApidClass::housekeeping;
        :>> source = ApplicationName::powerManagement; :>> rate = 0.1 [Hz]; :>> fieldCount = 24; :>> lengthOctets = 60;
        attribute f01 : PacketField { :>> order = 1; :>> offset = 96; :>> width = 16; :>> point = "EPS_BATT_CELL_V_01"; }
        attribute f02 : PacketField { :>> order = 2; :>> offset = 112; :>> width = 16; :>> point = "EPS_BATT_CELL_V_02"; }
        attribute f03 : PacketField { :>> order = 3; :>> offset = 128; :>> width = 16; :>> point = "EPS_BATT_CELL_V_03"; }
        attribute f04 : PacketField { :>> order = 4; :>> offset = 144; :>> width = 16; :>> point = "EPS_BATT_CELL_V_04"; }
        attribute f05 : PacketField { :>> order = 5; :>> offset = 160; :>> width = 16; :>> point = "EPS_BATT_CELL_V_05"; }
        attribute f06 : PacketField { :>> order = 6; :>> offset = 176; :>> width = 16; :>> point = "EPS_BATT_CELL_V_06"; }
        attribute f07 : PacketField { :>> order = 7; :>> offset = 192; :>> width = 16; :>> point = "EPS_BATT_CELL_V_07"; }
        attribute f08 : PacketField { :>> order = 8; :>> offset = 208; :>> width = 16; :>> point = "EPS_BATT_CELL_V_08"; }
        attribute f09 : PacketField { :>> order = 9; :>> offset = 224; :>> width = 16; :>> point = "EPS_BATT_CELL_V_09"; }
        attribute f10 : PacketField { :>> order = 10; :>> offset = 240; :>> width = 16; :>> point = "EPS_BATT_CELL_V_10"; }
        attribute f11 : PacketField { :>> order = 11; :>> offset = 256; :>> width = 16; :>> point = "EPS_BATT_CELL_V_11"; }
        attribute f12 : PacketField { :>> order = 12; :>> offset = 272; :>> width = 16; :>> point = "EPS_BATT_CELL_V_12"; }
        attribute f13 : PacketField { :>> order = 13; :>> offset = 288; :>> width = 16; :>> point = "EPS_BATT_CELL_V_13"; }
        attribute f14 : PacketField { :>> order = 14; :>> offset = 304; :>> width = 16; :>> point = "EPS_BATT_CELL_V_14"; }
        attribute f15 : PacketField { :>> order = 15; :>> offset = 320; :>> width = 16; :>> point = "EPS_BATT_CELL_V_15"; }
        attribute f16 : PacketField { :>> order = 16; :>> offset = 336; :>> width = 16; :>> point = "EPS_BATT_CELL_V_16"; }
        attribute f17 : PacketField { :>> order = 17; :>> offset = 352; :>> width = 16; :>> point = "EPS_BATT_CELL_V_17"; }
        attribute f18 : PacketField { :>> order = 18; :>> offset = 368; :>> width = 16; :>> point = "EPS_BATT_CELL_V_18"; }
        attribute f19 : PacketField { :>> order = 19; :>> offset = 384; :>> width = 16; :>> point = "EPS_BATT_CELL_V_19"; }
        attribute f20 : PacketField { :>> order = 20; :>> offset = 400; :>> width = 16; :>> point = "EPS_BATT_CELL_V_20"; }
        attribute f21 : PacketField { :>> order = 21; :>> offset = 416; :>> width = 16; :>> point = "EPS_BATT_CELL_V_21"; }
        attribute f22 : PacketField { :>> order = 22; :>> offset = 432; :>> width = 16; :>> point = "EPS_BATT_CELL_V_22"; }
        attribute f23 : PacketField { :>> order = 23; :>> offset = 448; :>> width = 16; :>> point = "EPS_BATT_CELL_V_23"; }
        attribute f24 : PacketField { :>> order = 24; :>> offset = 464; :>> width = 16; :>> point = "EPS_BATT_CELL_V_24"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item epsEngPacket02 : PacketDefinition {
        :>> packetId = 15; :>> mnemonic = "EPS_ENG_02"; :>> apid = 22; :>> apidClass = ApidClass::housekeeping;
        :>> source = ApplicationName::powerManagement; :>> rate = 0.1 [Hz]; :>> fieldCount = 24; :>> lengthOctets = 60;
        attribute f01 : PacketField { :>> order = 1; :>> offset = 96; :>> width = 16; :>> point = "EPS_BATT_CELL_V_25"; }
        attribute f02 : PacketField { :>> order = 2; :>> offset = 112; :>> width = 16; :>> point = "EPS_BATT_CELL_V_26"; }
        attribute f03 : PacketField { :>> order = 3; :>> offset = 128; :>> width = 16; :>> point = "EPS_BATT_CELL_V_27"; }
        attribute f04 : PacketField { :>> order = 4; :>> offset = 144; :>> width = 16; :>> point = "EPS_BATT_CELL_V_28"; }
        attribute f05 : PacketField { :>> order = 5; :>> offset = 160; :>> width = 16; :>> point = "EPS_BATT_CELL_V_29"; }
        attribute f06 : PacketField { :>> order = 6; :>> offset = 176; :>> width = 16; :>> point = "EPS_BATT_CELL_V_30"; }
        attribute f07 : PacketField { :>> order = 7; :>> offset = 192; :>> width = 16; :>> point = "EPS_BATT_CELL_V_31"; }
        attribute f08 : PacketField { :>> order = 8; :>> offset = 208; :>> width = 16; :>> point = "EPS_BATT_CELL_V_32"; }
        attribute f09 : PacketField { :>> order = 9; :>> offset = 224; :>> width = 16; :>> point = "EPS_ARRAY_STRING_I_01"; }
        attribute f10 : PacketField { :>> order = 10; :>> offset = 240; :>> width = 16; :>> point = "EPS_ARRAY_STRING_I_02"; }
        attribute f11 : PacketField { :>> order = 11; :>> offset = 256; :>> width = 16; :>> point = "EPS_ARRAY_STRING_I_03"; }
        attribute f12 : PacketField { :>> order = 12; :>> offset = 272; :>> width = 16; :>> point = "EPS_ARRAY_STRING_I_04"; }
        attribute f13 : PacketField { :>> order = 13; :>> offset = 288; :>> width = 16; :>> point = "EPS_ARRAY_STRING_I_05"; }
        attribute f14 : PacketField { :>> order = 14; :>> offset = 304; :>> width = 16; :>> point = "EPS_ARRAY_STRING_I_06"; }
        attribute f15 : PacketField { :>> order = 15; :>> offset = 320; :>> width = 16; :>> point = "EPS_ARRAY_STRING_I_07"; }
        attribute f16 : PacketField { :>> order = 16; :>> offset = 336; :>> width = 16; :>> point = "EPS_ARRAY_STRING_I_08"; }
        attribute f17 : PacketField { :>> order = 17; :>> offset = 352; :>> width = 16; :>> point = "EPS_ARRAY_STRING_I_09"; }
        attribute f18 : PacketField { :>> order = 18; :>> offset = 368; :>> width = 16; :>> point = "EPS_ARRAY_STRING_I_10"; }
        attribute f19 : PacketField { :>> order = 19; :>> offset = 384; :>> width = 16; :>> point = "EPS_ARRAY_STRING_I_11"; }
        attribute f20 : PacketField { :>> order = 20; :>> offset = 400; :>> width = 16; :>> point = "EPS_ARRAY_STRING_I_12"; }
        attribute f21 : PacketField { :>> order = 21; :>> offset = 416; :>> width = 16; :>> point = "EPS_ARRAY_STRING_I_13"; }
        attribute f22 : PacketField { :>> order = 22; :>> offset = 432; :>> width = 16; :>> point = "EPS_ARRAY_STRING_I_14"; }
        attribute f23 : PacketField { :>> order = 23; :>> offset = 448; :>> width = 16; :>> point = "EPS_ARRAY_STRING_I_15"; }
        attribute f24 : PacketField { :>> order = 24; :>> offset = 464; :>> width = 16; :>> point = "EPS_ARRAY_STRING_I_16"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item epsEngPacket03 : PacketDefinition {
        :>> packetId = 16; :>> mnemonic = "EPS_ENG_03"; :>> apid = 23; :>> apidClass = ApidClass::housekeeping;
        :>> source = ApplicationName::powerManagement; :>> rate = 1.0 [Hz]; :>> fieldCount = 24; :>> lengthOctets = 60;
        attribute f01 : PacketField { :>> order = 1; :>> offset = 96; :>> width = 16; :>> point = "EPS_ARRAY_STRING_I_17"; }
        attribute f02 : PacketField { :>> order = 2; :>> offset = 112; :>> width = 16; :>> point = "EPS_ARRAY_STRING_I_18"; }
        attribute f03 : PacketField { :>> order = 3; :>> offset = 128; :>> width = 16; :>> point = "EPS_ARRAY_STRING_I_19"; }
        attribute f04 : PacketField { :>> order = 4; :>> offset = 144; :>> width = 16; :>> point = "EPS_ARRAY_STRING_I_20"; }
        attribute f05 : PacketField { :>> order = 5; :>> offset = 160; :>> width = 16; :>> point = "EPS_ARRAY_STRING_I_21"; }
        attribute f06 : PacketField { :>> order = 6; :>> offset = 176; :>> width = 16; :>> point = "EPS_ARRAY_STRING_I_22"; }
        attribute f07 : PacketField { :>> order = 7; :>> offset = 192; :>> width = 16; :>> point = "EPS_ARRAY_STRING_I_23"; }
        attribute f08 : PacketField { :>> order = 8; :>> offset = 208; :>> width = 16; :>> point = "EPS_ARRAY_STRING_I_24"; }
        attribute f09 : PacketField { :>> order = 9; :>> offset = 224; :>> width = 16; :>> point = "EPS_ARRAY_T_01"; }
        attribute f10 : PacketField { :>> order = 10; :>> offset = 240; :>> width = 16; :>> point = "EPS_ARRAY_T_02"; }
        attribute f11 : PacketField { :>> order = 11; :>> offset = 256; :>> width = 16; :>> point = "EPS_ARRAY_T_03"; }
        attribute f12 : PacketField { :>> order = 12; :>> offset = 272; :>> width = 16; :>> point = "EPS_ARRAY_T_04"; }
        attribute f13 : PacketField { :>> order = 13; :>> offset = 288; :>> width = 16; :>> point = "EPS_ARRAY_T_05"; }
        attribute f14 : PacketField { :>> order = 14; :>> offset = 304; :>> width = 16; :>> point = "EPS_ARRAY_T_06"; }
        attribute f15 : PacketField { :>> order = 15; :>> offset = 320; :>> width = 16; :>> point = "EPS_ARRAY_T_07"; }
        attribute f16 : PacketField { :>> order = 16; :>> offset = 336; :>> width = 16; :>> point = "EPS_ARRAY_T_08"; }
        attribute f17 : PacketField { :>> order = 17; :>> offset = 352; :>> width = 16; :>> point = "EPS_SW_I_01"; }
        attribute f18 : PacketField { :>> order = 18; :>> offset = 368; :>> width = 16; :>> point = "EPS_SW_I_02"; }
        attribute f19 : PacketField { :>> order = 19; :>> offset = 384; :>> width = 16; :>> point = "EPS_SW_I_03"; }
        attribute f20 : PacketField { :>> order = 20; :>> offset = 400; :>> width = 16; :>> point = "EPS_SW_I_04"; }
        attribute f21 : PacketField { :>> order = 21; :>> offset = 416; :>> width = 16; :>> point = "EPS_SW_I_05"; }
        attribute f22 : PacketField { :>> order = 22; :>> offset = 432; :>> width = 16; :>> point = "EPS_SW_I_06"; }
        attribute f23 : PacketField { :>> order = 23; :>> offset = 448; :>> width = 16; :>> point = "EPS_SW_I_07"; }
        attribute f24 : PacketField { :>> order = 24; :>> offset = 464; :>> width = 16; :>> point = "EPS_SW_I_08"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item epsEngPacket04 : PacketDefinition {
        :>> packetId = 17; :>> mnemonic = "EPS_ENG_04"; :>> apid = 24; :>> apidClass = ApidClass::housekeeping;
        :>> source = ApplicationName::powerManagement; :>> rate = 1.0 [Hz]; :>> fieldCount = 18; :>> lengthOctets = 52;
        attribute f01 : PacketField { :>> order = 1; :>> offset = 96; :>> width = 16; :>> point = "EPS_SW_I_09"; }
        attribute f02 : PacketField { :>> order = 2; :>> offset = 112; :>> width = 16; :>> point = "EPS_SW_I_10"; }
        attribute f03 : PacketField { :>> order = 3; :>> offset = 128; :>> width = 16; :>> point = "EPS_SW_I_11"; }
        attribute f04 : PacketField { :>> order = 4; :>> offset = 144; :>> width = 16; :>> point = "EPS_SW_I_12"; }
        attribute f05 : PacketField { :>> order = 5; :>> offset = 160; :>> width = 16; :>> point = "EPS_SW_I_13"; }
        attribute f06 : PacketField { :>> order = 6; :>> offset = 176; :>> width = 16; :>> point = "EPS_SW_I_14"; }
        attribute f07 : PacketField { :>> order = 7; :>> offset = 192; :>> width = 16; :>> point = "EPS_SW_I_15"; }
        attribute f08 : PacketField { :>> order = 8; :>> offset = 208; :>> width = 16; :>> point = "EPS_SW_I_16"; }
        attribute f09 : PacketField { :>> order = 9; :>> offset = 224; :>> width = 16; :>> point = "EPS_SW_I_17"; }
        attribute f10 : PacketField { :>> order = 10; :>> offset = 240; :>> width = 16; :>> point = "EPS_SW_I_18"; }
        attribute f11 : PacketField { :>> order = 11; :>> offset = 256; :>> width = 16; :>> point = "EPS_SW_I_19"; }
        attribute f12 : PacketField { :>> order = 12; :>> offset = 272; :>> width = 16; :>> point = "EPS_SW_I_20"; }
        attribute f13 : PacketField { :>> order = 13; :>> offset = 288; :>> width = 16; :>> point = "EPS_SW_I_21"; }
        attribute f14 : PacketField { :>> order = 14; :>> offset = 304; :>> width = 16; :>> point = "EPS_SW_I_22"; }
        attribute f15 : PacketField { :>> order = 15; :>> offset = 320; :>> width = 16; :>> point = "EPS_SW_I_23"; }
        attribute f16 : PacketField { :>> order = 16; :>> offset = 336; :>> width = 16; :>> point = "EPS_SW_I_24"; }
        attribute f17 : PacketField { :>> order = 17; :>> offset = 352; :>> width = 32; :>> point = "EPS_SADA_RATE_01"; }
        attribute f18 : PacketField { :>> order = 18; :>> offset = 384; :>> width = 32; :>> point = "EPS_SADA_RATE_02"; }
        :>> widths = (f01.width, f02.width, f03.width, f04.width, f05.width, f06.width, f07.width, f08.width, f09.width, f10.width, f11.width, f12.width, f13.width, f14.width, f15.width, f16.width, f17.width, f18.width);
        :>> offsets = (f01.offset, f02.offset, f03.offset, f04.offset, f05.offset, f06.offset, f07.offset, f08.offset, f09.offset, f10.offset, f11.offset, f12.offset, f13.offset, f14.offset, f15.offset, f16.offset, f17.offset, f18.offset);
    }
    item thmHkPacket01 : PacketDefinition {
        :>> packetId = 18; :>> mnemonic = "THM_HK_01"; :>> apid = 25; :>> apidClass = ApidClass::housekeeping;
        :>> source = ApplicationName::thermalControl; :>> rate = 1.0 [Hz]; :>> fieldCount = 22; :>> lengthOctets = 39;
        attribute f01 : PacketField { :>> order = 1; :>> offset = 96; :>> width = 8; :>> point = "THM_HTR_STATE_01"; }
        attribute f02 : PacketField { :>> order = 2; :>> offset = 104; :>> width = 8; :>> point = "THM_HTR_STATE_02"; }
        attribute f03 : PacketField { :>> order = 3; :>> offset = 112; :>> width = 8; :>> point = "THM_HTR_STATE_03"; }
        attribute f04 : PacketField { :>> order = 4; :>> offset = 120; :>> width = 8; :>> point = "THM_HTR_STATE_04"; }
        attribute f05 : PacketField { :>> order = 5; :>> offset = 128; :>> width = 8; :>> point = "THM_HTR_STATE_05"; }
        attribute f06 : PacketField { :>> order = 6; :>> offset = 136; :>> width = 8; :>> point = "THM_HTR_STATE_06"; }
        attribute f07 : PacketField { :>> order = 7; :>> offset = 144; :>> width = 8; :>> point = "THM_HTR_STATE_07"; }
        attribute f08 : PacketField { :>> order = 8; :>> offset = 152; :>> width = 8; :>> point = "THM_HTR_STATE_08"; }
        attribute f09 : PacketField { :>> order = 9; :>> offset = 160; :>> width = 8; :>> point = "THM_HTR_STATE_09"; }
        attribute f10 : PacketField { :>> order = 10; :>> offset = 168; :>> width = 8; :>> point = "THM_HTR_STATE_10"; }
        attribute f11 : PacketField { :>> order = 11; :>> offset = 176; :>> width = 8; :>> point = "THM_HTR_STATE_11"; }
        attribute f12 : PacketField { :>> order = 12; :>> offset = 184; :>> width = 8; :>> point = "THM_HTR_STATE_12"; }
        attribute f13 : PacketField { :>> order = 13; :>> offset = 192; :>> width = 8; :>> point = "THM_HTR_STATE_13"; }
        attribute f14 : PacketField { :>> order = 14; :>> offset = 200; :>> width = 8; :>> point = "THM_HTR_STATE_14"; }
        attribute f15 : PacketField { :>> order = 15; :>> offset = 208; :>> width = 8; :>> point = "THM_HTR_STATE_15"; }
        attribute f16 : PacketField { :>> order = 16; :>> offset = 216; :>> width = 8; :>> point = "THM_HTR_STATE_16"; }
        attribute f17 : PacketField { :>> order = 17; :>> offset = 224; :>> width = 16; :>> point = "THM_RADIATOR_T_01"; }
        attribute f18 : PacketField { :>> order = 18; :>> offset = 240; :>> width = 16; :>> point = "THM_RADIATOR_T_02"; }
        attribute f19 : PacketField { :>> order = 19; :>> offset = 256; :>> width = 16; :>> point = "THM_RADIATOR_T_03"; }
        attribute f20 : PacketField { :>> order = 20; :>> offset = 272; :>> width = 16; :>> point = "THM_RADIATOR_T_04"; }
        attribute f21 : PacketField { :>> order = 21; :>> offset = 288; :>> width = 16; :>> point = "THM_HTR_POWER_TOTAL"; }
        attribute f22 : PacketField { :>> order = 22; :>> offset = 304; :>> width = 8; :>> point = "THM_CONTROL_MODE"; }
        :>> widths = (f01.width, f02.width, f03.width, f04.width, f05.width, f06.width, f07.width, f08.width, f09.width, f10.width, f11.width, f12.width, f13.width, f14.width, f15.width, f16.width, f17.width, f18.width, f19.width, f20.width, f21.width, f22.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset);
    }
    item thmEngPacket01 : PacketDefinition {
        :>> packetId = 19; :>> mnemonic = "THM_ENG_01"; :>> apid = 26; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_ZONE_T_01"; }
        attribute f02 : PacketField { :>> order = 2; :>> offset = 112; :>> width = 16; :>> point = "THM_ZONE_T_02"; }
        attribute f03 : PacketField { :>> order = 3; :>> offset = 128; :>> width = 16; :>> point = "THM_ZONE_T_03"; }
        attribute f04 : PacketField { :>> order = 4; :>> offset = 144; :>> width = 16; :>> point = "THM_ZONE_T_04"; }
        attribute f05 : PacketField { :>> order = 5; :>> offset = 160; :>> width = 16; :>> point = "THM_ZONE_T_05"; }
        attribute f06 : PacketField { :>> order = 6; :>> offset = 176; :>> width = 16; :>> point = "THM_ZONE_T_06"; }
        attribute f07 : PacketField { :>> order = 7; :>> offset = 192; :>> width = 16; :>> point = "THM_ZONE_T_07"; }
        attribute f08 : PacketField { :>> order = 8; :>> offset = 208; :>> width = 16; :>> point = "THM_ZONE_T_08"; }
        attribute f09 : PacketField { :>> order = 9; :>> offset = 224; :>> width = 16; :>> point = "THM_ZONE_T_09"; }
        attribute f10 : PacketField { :>> order = 10; :>> offset = 240; :>> width = 16; :>> point = "THM_ZONE_T_10"; }
        attribute f11 : PacketField { :>> order = 11; :>> offset = 256; :>> width = 16; :>> point = "THM_ZONE_T_11"; }
        attribute f12 : PacketField { :>> order = 12; :>> offset = 272; :>> width = 16; :>> point = "THM_ZONE_T_12"; }
        attribute f13 : PacketField { :>> order = 13; :>> offset = 288; :>> width = 16; :>> point = "THM_ZONE_T_13"; }
        attribute f14 : PacketField { :>> order = 14; :>> offset = 304; :>> width = 16; :>> point = "THM_ZONE_T_14"; }
        attribute f15 : PacketField { :>> order = 15; :>> offset = 320; :>> width = 16; :>> point = "THM_ZONE_T_15"; }
        attribute f16 : PacketField { :>> order = 16; :>> offset = 336; :>> width = 16; :>> point = "THM_ZONE_T_16"; }
        attribute f17 : PacketField { :>> order = 17; :>> offset = 352; :>> width = 16; :>> point = "THM_ZONE_T_17"; }
        attribute f18 : PacketField { :>> order = 18; :>> offset = 368; :>> width = 16; :>> point = "THM_ZONE_T_18"; }
        attribute f19 : PacketField { :>> order = 19; :>> offset = 384; :>> width = 16; :>> point = "THM_ZONE_T_19"; }
        attribute f20 : PacketField { :>> order = 20; :>> offset = 400; :>> width = 16; :>> point = "THM_ZONE_T_20"; }
        attribute f21 : PacketField { :>> order = 21; :>> offset = 416; :>> width = 16; :>> point = "THM_ZONE_T_21"; }
        attribute f22 : PacketField { :>> order = 22; :>> offset = 432; :>> width = 16; :>> point = "THM_ZONE_T_22"; }
        attribute f23 : PacketField { :>> order = 23; :>> offset = 448; :>> width = 16; :>> point = "THM_ZONE_T_23"; }
        attribute f24 : PacketField { :>> order = 24; :>> offset = 464; :>> width = 16; :>> point = "THM_ZONE_T_24"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket02 : PacketDefinition {
        :>> packetId = 20; :>> mnemonic = "THM_ENG_02"; :>> apid = 27; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_ZONE_T_25"; }
        attribute f02 : PacketField { :>> order = 2; :>> offset = 112; :>> width = 16; :>> point = "THM_ZONE_T_26"; }
        attribute f03 : PacketField { :>> order = 3; :>> offset = 128; :>> width = 16; :>> point = "THM_ZONE_T_27"; }
        attribute f04 : PacketField { :>> order = 4; :>> offset = 144; :>> width = 16; :>> point = "THM_ZONE_T_28"; }
        attribute f05 : PacketField { :>> order = 5; :>> offset = 160; :>> width = 16; :>> point = "THM_ZONE_T_29"; }
        attribute f06 : PacketField { :>> order = 6; :>> offset = 176; :>> width = 16; :>> point = "THM_ZONE_T_30"; }
        attribute f07 : PacketField { :>> order = 7; :>> offset = 192; :>> width = 16; :>> point = "THM_ZONE_T_31"; }
        attribute f08 : PacketField { :>> order = 8; :>> offset = 208; :>> width = 16; :>> point = "THM_ZONE_T_32"; }
        attribute f09 : PacketField { :>> order = 9; :>> offset = 224; :>> width = 16; :>> point = "THM_ZONE_T_33"; }
        attribute f10 : PacketField { :>> order = 10; :>> offset = 240; :>> width = 16; :>> point = "THM_ZONE_T_34"; }
        attribute f11 : PacketField { :>> order = 11; :>> offset = 256; :>> width = 16; :>> point = "THM_ZONE_T_35"; }
        attribute f12 : PacketField { :>> order = 12; :>> offset = 272; :>> width = 16; :>> point = "THM_ZONE_T_36"; }
        attribute f13 : PacketField { :>> order = 13; :>> offset = 288; :>> width = 16; :>> point = "THM_ZONE_T_37"; }
        attribute f14 : PacketField { :>> order = 14; :>> offset = 304; :>> width = 16; :>> point = "THM_ZONE_T_38"; }
        attribute f15 : PacketField { :>> order = 15; :>> offset = 320; :>> width = 16; :>> point = "THM_ZONE_T_39"; }
        attribute f16 : PacketField { :>> order = 16; :>> offset = 336; :>> width = 16; :>> point = "THM_ZONE_T_40"; }
        attribute f17 : PacketField { :>> order = 17; :>> offset = 352; :>> width = 16; :>> point = "THM_ZONE_T_41"; }
        attribute f18 : PacketField { :>> order = 18; :>> offset = 368; :>> width = 16; :>> point = "THM_ZONE_T_42"; }
        attribute f19 : PacketField { :>> order = 19; :>> offset = 384; :>> width = 16; :>> point = "THM_ZONE_T_43"; }
        attribute f20 : PacketField { :>> order = 20; :>> offset = 400; :>> width = 16; :>> point = "THM_ZONE_T_44"; }
        attribute f21 : PacketField { :>> order = 21; :>> offset = 416; :>> width = 16; :>> point = "THM_ZONE_T_45"; }
        attribute f22 : PacketField { :>> order = 22; :>> offset = 432; :>> width = 16; :>> point = "THM_ZONE_T_46"; }
        attribute f23 : PacketField { :>> order = 23; :>> offset = 448; :>> width = 16; :>> point = "THM_ZONE_T_47"; }
        attribute f24 : PacketField { :>> order = 24; :>> offset = 464; :>> width = 16; :>> point = "THM_ZONE_T_48"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket03 : PacketDefinition {
        :>> packetId = 21; :>> mnemonic = "THM_ENG_03"; :>> apid = 28; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_ZONE_T_49"; }
        attribute f02 : PacketField { :>> order = 2; :>> offset = 112; :>> width = 16; :>> point = "THM_ZONE_T_50"; }
        attribute f03 : PacketField { :>> order = 3; :>> offset = 128; :>> width = 16; :>> point = "THM_ZONE_T_51"; }
        attribute f04 : PacketField { :>> order = 4; :>> offset = 144; :>> width = 16; :>> point = "THM_ZONE_T_52"; }
        attribute f05 : PacketField { :>> order = 5; :>> offset = 160; :>> width = 16; :>> point = "THM_ZONE_T_53"; }
        attribute f06 : PacketField { :>> order = 6; :>> offset = 176; :>> width = 16; :>> point = "THM_ZONE_T_54"; }
        attribute f07 : PacketField { :>> order = 7; :>> offset = 192; :>> width = 16; :>> point = "THM_ZONE_T_55"; }
        attribute f08 : PacketField { :>> order = 8; :>> offset = 208; :>> width = 16; :>> point = "THM_ZONE_T_56"; }
        attribute f09 : PacketField { :>> order = 9; :>> offset = 224; :>> width = 16; :>> point = "THM_ZONE_T_57"; }
        attribute f10 : PacketField { :>> order = 10; :>> offset = 240; :>> width = 16; :>> point = "THM_ZONE_T_58"; }
        attribute f11 : PacketField { :>> order = 11; :>> offset = 256; :>> width = 16; :>> point = "THM_ZONE_T_59"; }
        attribute f12 : PacketField { :>> order = 12; :>> offset = 272; :>> width = 16; :>> point = "THM_ZONE_T_60"; }
        attribute f13 : PacketField { :>> order = 13; :>> offset = 288; :>> width = 16; :>> point = "THM_ZONE_T_61"; }
        attribute f14 : PacketField { :>> order = 14; :>> offset = 304; :>> width = 16; :>> point = "THM_ZONE_T_62"; }
        attribute f15 : PacketField { :>> order = 15; :>> offset = 320; :>> width = 16; :>> point = "THM_ZONE_T_63"; }
        attribute f16 : PacketField { :>> order = 16; :>> offset = 336; :>> width = 16; :>> point = "THM_ZONE_T_64"; }
        attribute f17 : PacketField { :>> order = 17; :>> offset = 352; :>> width = 16; :>> point = "THM_ZONE_T_65"; }
        attribute f18 : PacketField { :>> order = 18; :>> offset = 368; :>> width = 16; :>> point = "THM_ZONE_T_66"; }
        attribute f19 : PacketField { :>> order = 19; :>> offset = 384; :>> width = 16; :>> point = "THM_ZONE_T_67"; }
        attribute f20 : PacketField { :>> order = 20; :>> offset = 400; :>> width = 16; :>> point = "THM_ZONE_T_68"; }
        attribute f21 : PacketField { :>> order = 21; :>> offset = 416; :>> width = 16; :>> point = "THM_ZONE_T_69"; }
        attribute f22 : PacketField { :>> order = 22; :>> offset = 432; :>> width = 16; :>> point = "THM_ZONE_T_70"; }
        attribute f23 : PacketField { :>> order = 23; :>> offset = 448; :>> width = 16; :>> point = "THM_ZONE_T_71"; }
        attribute f24 : PacketField { :>> order = 24; :>> offset = 464; :>> width = 16; :>> point = "THM_ZONE_T_72"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket04 : PacketDefinition {
        :>> packetId = 22; :>> mnemonic = "THM_ENG_04"; :>> apid = 29; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_ZONE_T_73"; }
        attribute f02 : PacketField { :>> order = 2; :>> offset = 112; :>> width = 16; :>> point = "THM_ZONE_T_74"; }
        attribute f03 : PacketField { :>> order = 3; :>> offset = 128; :>> width = 16; :>> point = "THM_ZONE_T_75"; }
        attribute f04 : PacketField { :>> order = 4; :>> offset = 144; :>> width = 16; :>> point = "THM_ZONE_T_76"; }
        attribute f05 : PacketField { :>> order = 5; :>> offset = 160; :>> width = 16; :>> point = "THM_ZONE_T_77"; }
        attribute f06 : PacketField { :>> order = 6; :>> offset = 176; :>> width = 16; :>> point = "THM_ZONE_T_78"; }
        attribute f07 : PacketField { :>> order = 7; :>> offset = 192; :>> width = 16; :>> point = "THM_ZONE_T_79"; }
        attribute f08 : PacketField { :>> order = 8; :>> offset = 208; :>> width = 16; :>> point = "THM_ZONE_T_80"; }
        attribute f09 : PacketField { :>> order = 9; :>> offset = 224; :>> width = 16; :>> point = "THM_ZONE_T_81"; }
        attribute f10 : PacketField { :>> order = 10; :>> offset = 240; :>> width = 16; :>> point = "THM_ZONE_T_82"; }
        attribute f11 : PacketField { :>> order = 11; :>> offset = 256; :>> width = 16; :>> point = "THM_ZONE_T_83"; }
        attribute f12 : PacketField { :>> order = 12; :>> offset = 272; :>> width = 16; :>> point = "THM_ZONE_T_84"; }
        attribute f13 : PacketField { :>> order = 13; :>> offset = 288; :>> width = 16; :>> point = "THM_ZONE_T_85"; }
        attribute f14 : PacketField { :>> order = 14; :>> offset = 304; :>> width = 16; :>> point = "THM_ZONE_T_86"; }
        attribute f15 : PacketField { :>> order = 15; :>> offset = 320; :>> width = 16; :>> point = "THM_ZONE_T_87"; }
        attribute f16 : PacketField { :>> order = 16; :>> offset = 336; :>> width = 16; :>> point = "THM_ZONE_T_88"; }
        attribute f17 : PacketField { :>> order = 17; :>> offset = 352; :>> width = 16; :>> point = "THM_ZONE_T_89"; }
        attribute f18 : PacketField { :>> order = 18; :>> offset = 368; :>> width = 16; :>> point = "THM_ZONE_T_90"; }
        attribute f19 : PacketField { :>> order = 19; :>> offset = 384; :>> width = 16; :>> point = "THM_ZONE_T_91"; }
        attribute f20 : PacketField { :>> order = 20; :>> offset = 400; :>> width = 16; :>> point = "THM_ZONE_T_92"; }
        attribute f21 : PacketField { :>> order = 21; :>> offset = 416; :>> width = 16; :>> point = "THM_ZONE_T_93"; }
        attribute f22 : PacketField { :>> order = 22; :>> offset = 432; :>> width = 16; :>> point = "THM_ZONE_T_94"; }
        attribute f23 : PacketField { :>> order = 23; :>> offset = 448; :>> width = 16; :>> point = "THM_ZONE_T_95"; }
        attribute f24 : PacketField { :>> order = 24; :>> offset = 464; :>> width = 16; :>> point = "THM_ZONE_T_96"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket05 : PacketDefinition {
        :>> packetId = 23; :>> mnemonic = "THM_ENG_05"; :>> apid = 30; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_ZONE_T_97"; }
        attribute f02 : PacketField { :>> order = 2; :>> offset = 112; :>> width = 16; :>> point = "THM_ZONE_T_98"; }
        attribute f03 : PacketField { :>> order = 3; :>> offset = 128; :>> width = 16; :>> point = "THM_ZONE_T_99"; }
        attribute f04 : PacketField { :>> order = 4; :>> offset = 144; :>> width = 16; :>> point = "THM_ZONE_T_100"; }
        attribute f05 : PacketField { :>> order = 5; :>> offset = 160; :>> width = 16; :>> point = "THM_ZONE_T_101"; }
        attribute f06 : PacketField { :>> order = 6; :>> offset = 176; :>> width = 16; :>> point = "THM_ZONE_T_102"; }
        attribute f07 : PacketField { :>> order = 7; :>> offset = 192; :>> width = 16; :>> point = "THM_ZONE_T_103"; }
        attribute f08 : PacketField { :>> order = 8; :>> offset = 208; :>> width = 16; :>> point = "THM_ZONE_T_104"; }
        attribute f09 : PacketField { :>> order = 9; :>> offset = 224; :>> width = 16; :>> point = "THM_ZONE_T_105"; }
        attribute f10 : PacketField { :>> order = 10; :>> offset = 240; :>> width = 16; :>> point = "THM_ZONE_T_106"; }
        attribute f11 : PacketField { :>> order = 11; :>> offset = 256; :>> width = 16; :>> point = "THM_ZONE_T_107"; }
        attribute f12 : PacketField { :>> order = 12; :>> offset = 272; :>> width = 16; :>> point = "THM_ZONE_T_108"; }
        attribute f13 : PacketField { :>> order = 13; :>> offset = 288; :>> width = 16; :>> point = "THM_ZONE_T_109"; }
        attribute f14 : PacketField { :>> order = 14; :>> offset = 304; :>> width = 16; :>> point = "THM_ZONE_T_110"; }
        attribute f15 : PacketField { :>> order = 15; :>> offset = 320; :>> width = 16; :>> point = "THM_ZONE_T_111"; }
        attribute f16 : PacketField { :>> order = 16; :>> offset = 336; :>> width = 16; :>> point = "THM_ZONE_T_112"; }
        attribute f17 : PacketField { :>> order = 17; :>> offset = 352; :>> width = 16; :>> point = "THM_ZONE_T_113"; }
        attribute f18 : PacketField { :>> order = 18; :>> offset = 368; :>> width = 16; :>> point = "THM_ZONE_T_114"; }
        attribute f19 : PacketField { :>> order = 19; :>> offset = 384; :>> width = 16; :>> point = "THM_ZONE_T_115"; }
        attribute f20 : PacketField { :>> order = 20; :>> offset = 400; :>> width = 16; :>> point = "THM_ZONE_T_116"; }
        attribute f21 : PacketField { :>> order = 21; :>> offset = 416; :>> width = 16; :>> point = "THM_ZONE_T_117"; }
        attribute f22 : PacketField { :>> order = 22; :>> offset = 432; :>> width = 16; :>> point = "THM_ZONE_T_118"; }
        attribute f23 : PacketField { :>> order = 23; :>> offset = 448; :>> width = 16; :>> point = "THM_ZONE_T_119"; }
        attribute f24 : PacketField { :>> order = 24; :>> offset = 464; :>> width = 16; :>> point = "THM_ZONE_T_120"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket06 : PacketDefinition {
        :>> packetId = 24; :>> mnemonic = "THM_ENG_06"; :>> apid = 31; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_ZONE_T_121"; }
        attribute f02 : PacketField { :>> order = 2; :>> offset = 112; :>> width = 16; :>> point = "THM_ZONE_T_122"; }
        attribute f03 : PacketField { :>> order = 3; :>> offset = 128; :>> width = 16; :>> point = "THM_ZONE_T_123"; }
        attribute f04 : PacketField { :>> order = 4; :>> offset = 144; :>> width = 16; :>> point = "THM_ZONE_T_124"; }
        attribute f05 : PacketField { :>> order = 5; :>> offset = 160; :>> width = 16; :>> point = "THM_ZONE_T_125"; }
        attribute f06 : PacketField { :>> order = 6; :>> offset = 176; :>> width = 16; :>> point = "THM_ZONE_T_126"; }
        attribute f07 : PacketField { :>> order = 7; :>> offset = 192; :>> width = 16; :>> point = "THM_ZONE_T_127"; }
        attribute f08 : PacketField { :>> order = 8; :>> offset = 208; :>> width = 16; :>> point = "THM_ZONE_T_128"; }
        attribute f09 : PacketField { :>> order = 9; :>> offset = 224; :>> width = 16; :>> point = "THM_ZONE_T_129"; }
        attribute f10 : PacketField { :>> order = 10; :>> offset = 240; :>> width = 16; :>> point = "THM_ZONE_T_130"; }
        attribute f11 : PacketField { :>> order = 11; :>> offset = 256; :>> width = 16; :>> point = "THM_ZONE_T_131"; }
        attribute f12 : PacketField { :>> order = 12; :>> offset = 272; :>> width = 16; :>> point = "THM_ZONE_T_132"; }
        attribute f13 : PacketField { :>> order = 13; :>> offset = 288; :>> width = 16; :>> point = "THM_ZONE_T_133"; }
        attribute f14 : PacketField { :>> order = 14; :>> offset = 304; :>> width = 16; :>> point = "THM_ZONE_T_134"; }
        attribute f15 : PacketField { :>> order = 15; :>> offset = 320; :>> width = 16; :>> point = "THM_ZONE_T_135"; }
        attribute f16 : PacketField { :>> order = 16; :>> offset = 336; :>> width = 16; :>> point = "THM_ZONE_T_136"; }
        attribute f17 : PacketField { :>> order = 17; :>> offset = 352; :>> width = 16; :>> point = "THM_ZONE_T_137"; }
        attribute f18 : PacketField { :>> order = 18; :>> offset = 368; :>> width = 16; :>> point = "THM_ZONE_T_138"; }
        attribute f19 : PacketField { :>> order = 19; :>> offset = 384; :>> width = 16; :>> point = "THM_ZONE_T_139"; }
        attribute f20 : PacketField { :>> order = 20; :>> offset = 400; :>> width = 16; :>> point = "THM_ZONE_T_140"; }
        attribute f21 : PacketField { :>> order = 21; :>> offset = 416; :>> width = 16; :>> point = "THM_ZONE_T_141"; }
        attribute f22 : PacketField { :>> order = 22; :>> offset = 432; :>> width = 16; :>> point = "THM_ZONE_T_142"; }
        attribute f23 : PacketField { :>> order = 23; :>> offset = 448; :>> width = 16; :>> point = "THM_ZONE_T_143"; }
        attribute f24 : PacketField { :>> order = 24; :>> offset = 464; :>> width = 16; :>> point = "THM_ZONE_T_144"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket07 : PacketDefinition {
        :>> packetId = 25; :>> mnemonic = "THM_ENG_07"; :>> apid = 32; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_ZONE_T_145"; }
        attribute f02 : PacketField { :>> order = 2; :>> offset = 112; :>> width = 16; :>> point = "THM_ZONE_T_146"; }
        attribute f03 : PacketField { :>> order = 3; :>> offset = 128; :>> width = 16; :>> point = "THM_ZONE_T_147"; }
        attribute f04 : PacketField { :>> order = 4; :>> offset = 144; :>> width = 16; :>> point = "THM_ZONE_T_148"; }
        attribute f05 : PacketField { :>> order = 5; :>> offset = 160; :>> width = 16; :>> point = "THM_ZONE_T_149"; }
        attribute f06 : PacketField { :>> order = 6; :>> offset = 176; :>> width = 16; :>> point = "THM_ZONE_T_150"; }
        attribute f07 : PacketField { :>> order = 7; :>> offset = 192; :>> width = 16; :>> point = "THM_ZONE_T_151"; }
        attribute f08 : PacketField { :>> order = 8; :>> offset = 208; :>> width = 16; :>> point = "THM_ZONE_T_152"; }
        attribute f09 : PacketField { :>> order = 9; :>> offset = 224; :>> width = 16; :>> point = "THM_ZONE_T_153"; }
        attribute f10 : PacketField { :>> order = 10; :>> offset = 240; :>> width = 16; :>> point = "THM_ZONE_T_154"; }
        attribute f11 : PacketField { :>> order = 11; :>> offset = 256; :>> width = 16; :>> point = "THM_ZONE_T_155"; }
        attribute f12 : PacketField { :>> order = 12; :>> offset = 272; :>> width = 16; :>> point = "THM_ZONE_T_156"; }
        attribute f13 : PacketField { :>> order = 13; :>> offset = 288; :>> width = 16; :>> point = "THM_ZONE_T_157"; }
        attribute f14 : PacketField { :>> order = 14; :>> offset = 304; :>> width = 16; :>> point = "THM_ZONE_T_158"; }
        attribute f15 : PacketField { :>> order = 15; :>> offset = 320; :>> width = 16; :>> point = "THM_ZONE_T_159"; }
        attribute f16 : PacketField { :>> order = 16; :>> offset = 336; :>> width = 16; :>> point = "THM_ZONE_T_160"; }
        attribute f17 : PacketField { :>> order = 17; :>> offset = 352; :>> width = 16; :>> point = "THM_ZONE_T_161"; }
        attribute f18 : PacketField { :>> order = 18; :>> offset = 368; :>> width = 16; :>> point = "THM_ZONE_T_162"; }
        attribute f19 : PacketField { :>> order = 19; :>> offset = 384; :>> width = 16; :>> point = "THM_ZONE_T_163"; }
        attribute f20 : PacketField { :>> order = 20; :>> offset = 400; :>> width = 16; :>> point = "THM_ZONE_T_164"; }
        attribute f21 : PacketField { :>> order = 21; :>> offset = 416; :>> width = 16; :>> point = "THM_ZONE_T_165"; }
        attribute f22 : PacketField { :>> order = 22; :>> offset = 432; :>> width = 16; :>> point = "THM_ZONE_T_166"; }
        attribute f23 : PacketField { :>> order = 23; :>> offset = 448; :>> width = 16; :>> point = "THM_ZONE_T_167"; }
        attribute f24 : PacketField { :>> order = 24; :>> offset = 464; :>> width = 16; :>> point = "THM_ZONE_T_168"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket08 : PacketDefinition {
        :>> packetId = 26; :>> mnemonic = "THM_ENG_08"; :>> apid = 33; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_ZONE_T_169"; }
        attribute f02 : PacketField { :>> order = 2; :>> offset = 112; :>> width = 16; :>> point = "THM_ZONE_T_170"; }
        attribute f03 : PacketField { :>> order = 3; :>> offset = 128; :>> width = 16; :>> point = "THM_ZONE_T_171"; }
        attribute f04 : PacketField { :>> order = 4; :>> offset = 144; :>> width = 16; :>> point = "THM_ZONE_T_172"; }
        attribute f05 : PacketField { :>> order = 5; :>> offset = 160; :>> width = 16; :>> point = "THM_ZONE_T_173"; }
        attribute f06 : PacketField { :>> order = 6; :>> offset = 176; :>> width = 16; :>> point = "THM_ZONE_T_174"; }
        attribute f07 : PacketField { :>> order = 7; :>> offset = 192; :>> width = 16; :>> point = "THM_ZONE_T_175"; }
        attribute f08 : PacketField { :>> order = 8; :>> offset = 208; :>> width = 16; :>> point = "THM_ZONE_T_176"; }
        attribute f09 : PacketField { :>> order = 9; :>> offset = 224; :>> width = 16; :>> point = "THM_ZONE_T_177"; }
        attribute f10 : PacketField { :>> order = 10; :>> offset = 240; :>> width = 16; :>> point = "THM_ZONE_T_178"; }
        attribute f11 : PacketField { :>> order = 11; :>> offset = 256; :>> width = 16; :>> point = "THM_ZONE_T_179"; }
        attribute f12 : PacketField { :>> order = 12; :>> offset = 272; :>> width = 16; :>> point = "THM_ZONE_T_180"; }
        attribute f13 : PacketField { :>> order = 13; :>> offset = 288; :>> width = 16; :>> point = "THM_ZONE_T_181"; }
        attribute f14 : PacketField { :>> order = 14; :>> offset = 304; :>> width = 16; :>> point = "THM_ZONE_T_182"; }
        attribute f15 : PacketField { :>> order = 15; :>> offset = 320; :>> width = 16; :>> point = "THM_ZONE_T_183"; }
        attribute f16 : PacketField { :>> order = 16; :>> offset = 336; :>> width = 16; :>> point = "THM_ZONE_T_184"; }
        attribute f17 : PacketField { :>> order = 17; :>> offset = 352; :>> width = 16; :>> point = "THM_ZONE_T_185"; }
        attribute f18 : PacketField { :>> order = 18; :>> offset = 368; :>> width = 16; :>> point = "THM_ZONE_T_186"; }
        attribute f19 : PacketField { :>> order = 19; :>> offset = 384; :>> width = 16; :>> point = "THM_ZONE_T_187"; }
        attribute f20 : PacketField { :>> order = 20; :>> offset = 400; :>> width = 16; :>> point = "THM_ZONE_T_188"; }
        attribute f21 : PacketField { :>> order = 21; :>> offset = 416; :>> width = 16; :>> point = "THM_ZONE_T_189"; }
        attribute f22 : PacketField { :>> order = 22; :>> offset = 432; :>> width = 16; :>> point = "THM_ZONE_T_190"; }
        attribute f23 : PacketField { :>> order = 23; :>> offset = 448; :>> width = 16; :>> point = "THM_ZONE_T_191"; }
        attribute f24 : PacketField { :>> order = 24; :>> offset = 464; :>> width = 16; :>> point = "THM_ZONE_T_192"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket09 : PacketDefinition {
        :>> packetId = 27; :>> mnemonic = "THM_ENG_09"; :>> apid = 34; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_HTR_DUTY_01"; }
        attribute f02 : PacketField { :>> order = 2; :>> offset = 112; :>> width = 16; :>> point = "THM_HTR_DUTY_02"; }
        attribute f03 : PacketField { :>> order = 3; :>> offset = 128; :>> width = 16; :>> point = "THM_HTR_DUTY_03"; }
        attribute f04 : PacketField { :>> order = 4; :>> offset = 144; :>> width = 16; :>> point = "THM_HTR_DUTY_04"; }
        attribute f05 : PacketField { :>> order = 5; :>> offset = 160; :>> width = 16; :>> point = "THM_HTR_DUTY_05"; }
        attribute f06 : PacketField { :>> order = 6; :>> offset = 176; :>> width = 16; :>> point = "THM_HTR_DUTY_06"; }
        attribute f07 : PacketField { :>> order = 7; :>> offset = 192; :>> width = 16; :>> point = "THM_HTR_DUTY_07"; }
        attribute f08 : PacketField { :>> order = 8; :>> offset = 208; :>> width = 16; :>> point = "THM_HTR_DUTY_08"; }
        attribute f09 : PacketField { :>> order = 9; :>> offset = 224; :>> width = 16; :>> point = "THM_HTR_DUTY_09"; }
        attribute f10 : PacketField { :>> order = 10; :>> offset = 240; :>> width = 16; :>> point = "THM_HTR_DUTY_10"; }
        attribute f11 : PacketField { :>> order = 11; :>> offset = 256; :>> width = 16; :>> point = "THM_HTR_DUTY_11"; }
        attribute f12 : PacketField { :>> order = 12; :>> offset = 272; :>> width = 16; :>> point = "THM_HTR_DUTY_12"; }
        attribute f13 : PacketField { :>> order = 13; :>> offset = 288; :>> width = 16; :>> point = "THM_HTR_DUTY_13"; }
        attribute f14 : PacketField { :>> order = 14; :>> offset = 304; :>> width = 16; :>> point = "THM_HTR_DUTY_14"; }
        attribute f15 : PacketField { :>> order = 15; :>> offset = 320; :>> width = 16; :>> point = "THM_HTR_DUTY_15"; }
        attribute f16 : PacketField { :>> order = 16; :>> offset = 336; :>> width = 16; :>> point = "THM_HTR_DUTY_16"; }
        attribute f17 : PacketField { :>> order = 17; :>> offset = 352; :>> width = 16; :>> point = "THM_HTR_I_01"; }
        attribute f18 : PacketField { :>> order = 18; :>> offset = 368; :>> width = 16; :>> point = "THM_HTR_I_02"; }
        attribute f19 : PacketField { :>> order = 19; :>> offset = 384; :>> width = 16; :>> point = "THM_HTR_I_03"; }
        attribute f20 : PacketField { :>> order = 20; :>> offset = 400; :>> width = 16; :>> point = "THM_HTR_I_04"; }
        attribute f21 : PacketField { :>> order = 21; :>> offset = 416; :>> width = 16; :>> point = "THM_HTR_I_05"; }
        attribute f22 : PacketField { :>> order = 22; :>> offset = 432; :>> width = 16; :>> point = "THM_HTR_I_06"; }
        attribute f23 : PacketField { :>> order = 23; :>> offset = 448; :>> width = 16; :>> point = "THM_HTR_I_07"; }
        attribute f24 : PacketField { :>> order = 24; :>> offset = 464; :>> width = 16; :>> point = "THM_HTR_I_08"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket10 : PacketDefinition {
        :>> packetId = 28; :>> mnemonic = "THM_ENG_10"; :>> apid = 35; :>> apidClass = ApidClass::housekeeping;
        :>> source = ApplicationName::thermalControl; :>> rate = 0.1 [Hz]; :>> fieldCount = 24; :>> lengthOctets = 60;
        attribute f01 : PacketField { :>> order = 1; :>> offset = 96; :>> width = 16; :>> point = "THM_HTR_I_09"; }
        attribute f02 : PacketField { :>> order = 2; :>> offset = 112; :>> width = 16; :>> point = "THM_HTR_I_10"; }
        attribute f03 : PacketField { :>> order = 3; :>> offset = 128; :>> width = 16; :>> point = "THM_HTR_I_11"; }
        attribute f04 : PacketField { :>> order = 4; :>> offset = 144; :>> width = 16; :>> point = "THM_HTR_I_12"; }
        attribute f05 : PacketField { :>> order = 5; :>> offset = 160; :>> width = 16; :>> point = "THM_HTR_I_13"; }
        attribute f06 : PacketField { :>> order = 6; :>> offset = 176; :>> width = 16; :>> point = "THM_HTR_I_14"; }
        attribute f07 : PacketField { :>> order = 7; :>> offset = 192; :>> width = 16; :>> point = "THM_HTR_I_15"; }
        attribute f08 : PacketField { :>> order = 8; :>> offset = 208; :>> width = 16; :>> point = "THM_HTR_I_16"; }
        attribute f09 : PacketField { :>> order = 9; :>> offset = 224; :>> width = 16; :>> point = "THM_SETPOINT_01"; }
        attribute f10 : PacketField { :>> order = 10; :>> offset = 240; :>> width = 16; :>> point = "THM_SETPOINT_02"; }
        attribute f11 : PacketField { :>> order = 11; :>> offset = 256; :>> width = 16; :>> point = "THM_SETPOINT_03"; }
        attribute f12 : PacketField { :>> order = 12; :>> offset = 272; :>> width = 16; :>> point = "THM_SETPOINT_04"; }
        attribute f13 : PacketField { :>> order = 13; :>> offset = 288; :>> width = 16; :>> point = "THM_SETPOINT_05"; }
        attribute f14 : PacketField { :>> order = 14; :>> offset = 304; :>> width = 16; :>> point = "THM_SETPOINT_06"; }
        attribute f15 : PacketField { :>> order = 15; :>> offset = 320; :>> width = 16; :>> point = "THM_SETPOINT_07"; }
        attribute f16 : PacketField { :>> order = 16; :>> offset = 336; :>> width = 16; :>> point = "THM_SETPOINT_08"; }
        attribute f17 : PacketField { :>> order = 17; :>> offset = 352; :>> width = 16; :>> point = "THM_SETPOINT_09"; }
        attribute f18 : PacketField { :>> order = 18; :>> offset = 368; :>> width = 16; :>> point = "THM_SETPOINT_10"; }
        attribute f19 : PacketField { :>> order = 19; :>> offset = 384; :>> width = 16; :>> point = "THM_SETPOINT_11"; }
        attribute f20 : PacketField { :>> order = 20; :>> offset = 400; :>> width = 16; :>> point = "THM_SETPOINT_12"; }
        attribute f21 : PacketField { :>> order = 21; :>> offset = 416; :>> width = 16; :>> point = "THM_SETPOINT_13"; }
        attribute f22 : PacketField { :>> order = 22; :>> offset = 432; :>> width = 16; :>> point = "THM_SETPOINT_14"; }
        attribute f23 : PacketField { :>> order = 23; :>> offset = 448; :>> width = 16; :>> point = "THM_SETPOINT_15"; }
        attribute f24 : PacketField { :>> order = 24; :>> offset = 464; :>> width = 16; :>> point = "THM_SETPOINT_16"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item thmEngPacket11 : PacketDefinition {
        :>> packetId = 29; :>> mnemonic = "THM_ENG_11"; :>> apid = 36; :>> apidClass = ApidClass::housekeeping;
        :>> source = ApplicationName::thermalControl; :>> rate = 0.1 [Hz]; :>> fieldCount = 12; :>> lengthOctets = 36;
        attribute f01 : PacketField { :>> order = 1; :>> offset = 96; :>> width = 16; :>> point = "THM_LOUVER_POS_01"; }
        attribute f02 : PacketField { :>> order = 2; :>> offset = 112; :>> width = 16; :>> point = "THM_LOUVER_POS_02"; }
        attribute f03 : PacketField { :>> order = 3; :>> offset = 128; :>> width = 16; :>> point = "THM_LOUVER_POS_03"; }
        attribute f04 : PacketField { :>> order = 4; :>> offset = 144; :>> width = 16; :>> point = "THM_LOUVER_POS_04"; }
        attribute f05 : PacketField { :>> order = 5; :>> offset = 160; :>> width = 16; :>> point = "THM_HEAT_PIPE_T_01"; }
        attribute f06 : PacketField { :>> order = 6; :>> offset = 176; :>> width = 16; :>> point = "THM_HEAT_PIPE_T_02"; }
        attribute f07 : PacketField { :>> order = 7; :>> offset = 192; :>> width = 16; :>> point = "THM_HEAT_PIPE_T_03"; }
        attribute f08 : PacketField { :>> order = 8; :>> offset = 208; :>> width = 16; :>> point = "THM_HEAT_PIPE_T_04"; }
        attribute f09 : PacketField { :>> order = 9; :>> offset = 224; :>> width = 16; :>> point = "THM_HEAT_PIPE_T_05"; }
        attribute f10 : PacketField { :>> order = 10; :>> offset = 240; :>> width = 16; :>> point = "THM_HEAT_PIPE_T_06"; }
        attribute f11 : PacketField { :>> order = 11; :>> offset = 256; :>> width = 16; :>> point = "THM_HEAT_PIPE_T_07"; }
        attribute f12 : PacketField { :>> order = 12; :>> offset = 272; :>> width = 16; :>> point = "THM_HEAT_PIPE_T_08"; }
        :>> widths = (f01.width, f02.width, f03.width, f04.width, f05.width, f06.width, f07.width, f08.width, f09.width, f10.width, f11.width, f12.width);
        :>> offsets = (f01.offset, f02.offset, f03.offset, f04.offset, f05.offset, f06.offset, f07.offset, f08.offset, f09.offset, f10.offset, f11.offset, f12.offset);
    }
    item comHkPacket01 : PacketDefinition {
        :>> packetId = 30; :>> mnemonic = "COM_HK_01"; :>> apid = 256; :>> apidClass = ApidClass::relay;
        :>> source = ApplicationName::telecom; :>> rate = 1.0 [Hz]; :>> fieldCount = 19; :>> lengthOctets = 48;
        attribute f01 : PacketField { :>> order = 1; :>> offset = 96; :>> width = 16; :>> point = "COM_TX_POWER_01"; }
        attribute f02 : PacketField { :>> order = 2; :>> offset = 112; :>> width = 16; :>> point = "COM_TX_POWER_02"; }
        attribute f03 : PacketField { :>> order = 3; :>> offset = 128; :>> width = 16; :>> point = "COM_RX_AGC_01"; }
        attribute f04 : PacketField { :>> order = 4; :>> offset = 144; :>> width = 16; :>> point = "COM_RX_AGC_02"; }
        attribute f05 : PacketField { :>> order = 5; :>> offset = 160; :>> width = 8; :>> point = "COM_RX_LOCK_01"; }
        attribute f06 : PacketField { :>> order = 6; :>> offset = 168; :>> width = 8; :>> point = "COM_RX_LOCK_02"; }
        attribute f07 : PacketField { :>> order = 7; :>> offset = 176; :>> width = 8; :>> point = "COM_CARRIER_LOCK"; }
        attribute f08 : PacketField { :>> order = 8; :>> offset = 184; :>> width = 32; :>> point = "COM_SYMBOL_RATE"; }
        attribute f09 : PacketField { :>> order = 9; :>> offset = 216; :>> width = 16; :>> point = "COM_SSPA_T_01"; }
        attribute f10 : PacketField { :>> order = 10; :>> offset = 232; :>> width = 16; :>> point = "COM_SSPA_T_02"; }
        attribute f11 : PacketField { :>> order = 11; :>> offset = 248; :>> width = 32; :>> point = "COM_HGA_AZ"; }
        attribute f12 : PacketField { :>> order = 12; :>> offset = 280; :>> width = 32; :>> point = "COM_HGA_EL"; }
        attribute f13 : PacketField { :>> order = 13; :>> offset = 312; :>> width = 8; :>> point = "COM_ANTENNA_SEL"; }
        attribute f14 : PacketField { :>> order = 14; :>> offset = 320; :>> width = 8; :>> point = "COM_RANGING_STATE"; }
        attribute f15 : PacketField { :>> order = 15; :>> offset = 328; :>> width = 16; :>> point = "COM_LINK_MARGIN"; }
        attribute f16 : PacketField { :>> order = 16; :>> offset = 344; :>> width = 8; :>> point = "COM_XPDR_STATE_01"; }
        attribute f17 : PacketField { :>> order = 17; :>> offset = 352; :>> width = 8; :>> point = "COM_XPDR_STATE_02"; }
        attribute f18 : PacketField { :>> order = 18; :>> offset = 360; :>> width = 8; :>> point = "COM_RELAY_RX_LOCK"; }
        attribute f19 : PacketField { :>> order = 19; :>> offset = 368; :>> width = 16; :>> point = "COM_RELAY_LINK_MARGIN"; }
        :>> widths = (f01.width, f02.width, f03.width, f04.width, f05.width, f06.width, f07.width, f08.width, f09.width, f10.width, f11.width, f12.width, f13.width, f14.width, f15.width, f16.width, f17.width, f18.width, f19.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset);
    }
    item comEngPacket01 : PacketDefinition {
        :>> packetId = 31; :>> mnemonic = "COM_ENG_01"; :>> apid = 257; :>> apidClass = ApidClass::relay;
        :>> source = ApplicationName::telecom; :>> rate = 1.0 [Hz]; :>> fieldCount = 17; :>> lengthOctets = 59;
        attribute f01 : PacketField { :>> order = 1; :>> offset = 96; :>> width = 32; :>> point = "COM_UPLINK_RATE"; }
        attribute f02 : PacketField { :>> order = 2; :>> offset = 128; :>> width = 32; :>> point = "COM_FRAME_COUNT"; }
        attribute f03 : PacketField { :>> order = 3; :>> offset = 160; :>> width = 32; :>> point = "COM_FRAME_ERRORS"; }
        attribute f04 : PacketField { :>> order = 4; :>> offset = 192; :>> width = 16; :>> point = "COM_SSPA_I_01"; }
        attribute f05 : PacketField { :>> order = 5; :>> offset = 208; :>> width = 16; :>> point = "COM_SSPA_I_02"; }
        attribute f06 : PacketField { :>> order = 6; :>> offset = 224; :>> width = 16; :>> point = "COM_DOPPLER"; }
        attribute f07 : PacketField { :>> order = 7; :>> offset = 240; :>> width = 32; :>> point = "COM_TWO_WAY_RANGE"; }
        attribute f08 : PacketField { :>> order = 8; :>> offset = 272; :>> width = 32; :>> point = "COM_PASS_REMAINING"; }
        attribute f09 : PacketField { :>> order = 9; :>> offset = 304; :>> width = 16; :>> point = "COM_EXCITER_T_01"; }
        attribute f10 : PacketField { :>> order = 10; :>> offset = 320; :>> width = 16; :>> point = "COM_EXCITER_T_02"; }
        attribute f11 : PacketField { :>> order = 11; :>> offset = 336; :>> width = 16; :>> point = "COM_HGA_T_01"; }
        attribute f12 : PacketField { :>> order = 12; :>> offset = 352; :>> width = 16; :>> point = "COM_HGA_T_02"; }
        attribute f13 : PacketField { :>> order = 13; :>> offset = 368; :>> width = 32; :>> point = "COM_RELAY_RATE"; }
        attribute f14 : PacketField { :>> order = 14; :>> offset = 400; :>> width = 32; :>> point = "COM_RELAY_FRAME_COUNT"; }
        attribute f15 : PacketField { :>> order = 15; :>> offset = 432; :>> width = 8; :>> point = "COM_CODING_SEL"; }
        attribute f16 : PacketField { :>> order = 16; :>> offset = 440; :>> width = 16; :>> point = "COM_HGA_MOTOR_I_01"; }
        attribute f17 : PacketField { :>> order = 17; :>> offset = 456; :>> width = 16; :>> point = "COM_HGA_MOTOR_I_02"; }
        :>> widths = (f01.width, f02.width, f03.width, f04.width, f05.width, f06.width, f07.width, f08.width, f09.width, f10.width, f11.width, f12.width, f13.width, f14.width, f15.width, f16.width, f17.width);
        :>> offsets = (f01.offset, f02.offset, f03.offset, f04.offset, f05.offset, f06.offset, f07.offset, f08.offset, f09.offset, f10.offset, f11.offset, f12.offset, f13.offset, f14.offset, f15.offset, f16.offset, f17.offset);
    }
    item insHkPacket01 : PacketDefinition {
        :>> packetId = 32; :>> mnemonic = "INS_HK_01"; :>> apid = 320; :>> apidClass = ApidClass::imaging;
        :>> source = ApplicationName::inspectorHandling; :>> rate = 1.0 [Hz]; :>> fieldCount = 12; :>> lengthOctets = 43;
        attribute f01 : PacketField { :>> order = 1; :>> offset = 96; :>> width = 32; :>> point = "INS_INSP_RANGE"; }
        attribute f02 : PacketField { :>> order = 2; :>> offset = 128; :>> width = 32; :>> point = "INS_INSP_BEARING_01"; }
        attribute f03 : PacketField { :>> order = 3; :>> offset = 160; :>> width = 32; :>> point = "INS_INSP_BEARING_02"; }
        attribute f04 : PacketField { :>> order = 4; :>> offset = 192; :>> width = 32; :>> point = "INS_INSP_RANGE_RATE"; }
        attribute f05 : PacketField { :>> order = 5; :>> offset = 224; :>> width = 8; :>> point = "INS_INSP_STATE"; }
        attribute f06 : PacketField { :>> order = 6; :>> offset = 232; :>> width = 16; :>> point = "INS_INSP_BATT_V"; }
        attribute f07 : PacketField { :>> order = 7; :>> offset = 248; :>> width = 16; :>> point = "INS_INSP_BATT_SOC"; }
        attribute f08 : PacketField { :>> order = 8; :>> offset = 264; :>> width = 16; :>> point = "INS_RELAY_MARGIN"; }
        attribute f09 : PacketField { :>> order = 9; :>> offset = 280; :>> width = 16; :>> point = "INS_INSP_PROPELLANT"; }
        attribute f10 : PacketField { :>> order = 10; :>> offset = 296; :>> width = 8; :>> point = "INS_RELEASE_MECH_STATE"; }
        attribute f11 : PacketField { :>> order = 11; :>> offset = 304; :>> width = 8; :>> point = "INS_RELEASE_ARMED"; }
        attribute f12 : PacketField { :>> order = 12; :>> offset = 312; :>> width = 32; :>> point = "INS_LAST_CONTACT_AGE"; }
        :>> widths = (f01.width, f02.width, f03.width, f04.width, f05.width, f06.width, f07.width, f08.width, f09.width, f10.width, f11.width, f12.width);
        :>> offsets = (f01.offset, f02.offset, f03.offset, f04.offset, f05.offset, f06.offset, f07.offset, f08.offset, f09.offset, f10.offset, f11.offset, f12.offset);
    }
    item insEngPacket01 : PacketDefinition {
        :>> packetId = 33; :>> mnemonic = "INS_ENG_01"; :>> apid = 321; :>> apidClass = ApidClass::imaging;
        :>> source = ApplicationName::inspectorHandling; :>> rate = 1.0 [Hz]; :>> fieldCount = 24; :>> lengthOctets = 82;
        attribute f01 : PacketField { :>> order = 1; :>> offset = 96; :>> width = 16; :>> point = "INS_INSP_T_01"; }
        attribute f02 : PacketField { :>> order = 2; :>> offset = 112; :>> width = 16; :>> point = "INS_INSP_T_02"; }
        attribute f03 : PacketField { :>> order = 3; :>> offset = 128; :>> width = 16; :>> point = "INS_INSP_T_03"; }
        attribute f04 : PacketField { :>> order = 4; :>> offset = 144; :>> width = 16; :>> point = "INS_INSP_T_04"; }
        attribute f05 : PacketField { :>> order = 5; :>> offset = 160; :>> width = 16; :>> point = "INS_INSP_T_05"; }
        attribute f06 : PacketField { :>> order = 6; :>> offset = 176; :>> width = 16; :>> point = "INS_INSP_T_06"; }
        attribute f07 : PacketField { :>> order = 7; :>> offset = 192; :>> width = 16; :>> point = "INS_INSP_T_07"; }
        attribute f08 : PacketField { :>> order = 8; :>> offset = 208; :>> width = 16; :>> point = "INS_INSP_T_08"; }
        attribute f09 : PacketField { :>> order = 9; :>> offset = 224; :>> width = 32; :>> point = "INS_IMAGE_COUNT"; }
        attribute f10 : PacketField { :>> order = 10; :>> offset = 256; :>> width = 32; :>> point = "INS_IMAGE_QUEUE"; }
        attribute f11 : PacketField { :>> order = 11; :>> offset = 288; :>> width = 32; :>> point = "INS_SEGMENTS_RX"; }
        attribute f12 : PacketField { :>> order = 12; :>> offset = 320; :>> width = 32; :>> point = "INS_SEGMENT_ERRORS"; }
        attribute f13 : PacketField { :>> order = 13; :>> offset = 352; :>> width = 16; :>> point = "INS_CAM_T_01"; }
        attribute f14 : PacketField { :>> order = 14; :>> offset = 368; :>> width = 16; :>> point = "INS_CAM_T_02"; }
        attribute f15 : PacketField { :>> order = 15; :>> offset = 384; :>> width = 8; :>> point = "INS_CAM_STATE_01"; }
        attribute f16 : PacketField { :>> order = 16; :>> offset = 392; :>> width = 8; :>> point = "INS_CAM_STATE_02"; }
        attribute f17 : PacketField { :>> order = 17; :>> offset = 400; :>> width = 32; :>> point = "INS_INSP_THR_PULSES_01"; }
        attribute f18 : PacketField { :>> order = 18; :>> offset = 432; :>> width = 32; :>> point = "INS_INSP_THR_PULSES_02"; }
        attribute f19 : PacketField { :>> order = 19; :>> offset = 464; :>> width = 32; :>> point = "INS_INSP_THR_PULSES_03"; }
        attribute f20 : PacketField { :>> order = 20; :>> offset = 496; :>> width = 32; :>> point = "INS_INSP_THR_PULSES_04"; }
        attribute f21 : PacketField { :>> order = 21; :>> offset = 528; :>> width = 32; :>> point = "INS_INSP_THR_PULSES_05"; }
        attribute f22 : PacketField { :>> order = 22; :>> offset = 560; :>> width = 32; :>> point = "INS_INSP_THR_PULSES_06"; }
        attribute f23 : PacketField { :>> order = 23; :>> offset = 592; :>> width = 32; :>> point = "INS_INSP_THR_PULSES_07"; }
        attribute f24 : PacketField { :>> order = 24; :>> offset = 624; :>> width = 32; :>> point = "INS_INSP_THR_PULSES_08"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item insEngPacket02 : PacketDefinition {
        :>> packetId = 34; :>> mnemonic = "INS_ENG_02"; :>> apid = 322; :>> apidClass = ApidClass::imaging;
        :>> source = ApplicationName::inspectorHandling; :>> rate = 0.1 [Hz]; :>> fieldCount = 1; :>> lengthOctets = 13;
        attribute f01 : PacketField { :>> order = 1; :>> offset = 96; :>> width = 8; :>> point = "INS_IMAGE_COMPRESSION"; }
        :>> widths = (f01.width);
        :>> offsets = (f01.offset);
    }
    item capHkPacket01 : PacketDefinition {
        :>> packetId = 35; :>> mnemonic = "CAP_HK_01"; :>> apid = 192; :>> apidClass = ApidClass::capture;
        :>> source = ApplicationName::captureControl; :>> rate = 10.0 [Hz]; :>> fieldCount = 24; :>> lengthOctets = 68;
        attribute f01 : PacketField { :>> order = 1; :>> offset = 96; :>> width = 16; :>> point = "CAP_BAG_DEPLOY_POS_01"; }
        attribute f02 : PacketField { :>> order = 2; :>> offset = 112; :>> width = 16; :>> point = "CAP_BAG_DEPLOY_POS_02"; }
        attribute f03 : PacketField { :>> order = 3; :>> offset = 128; :>> width = 16; :>> point = "CAP_BAG_DEPLOY_POS_03"; }
        attribute f04 : PacketField { :>> order = 4; :>> offset = 144; :>> width = 16; :>> point = "CAP_BAG_DEPLOY_POS_04"; }
        attribute f05 : PacketField { :>> order = 5; :>> offset = 160; :>> width = 32; :>> point = "CAP_PETAL_ANGLE_01"; }
        attribute f06 : PacketField { :>> order = 6; :>> offset = 192; :>> width = 32; :>> point = "CAP_PETAL_ANGLE_02"; }
        attribute f07 : PacketField { :>> order = 7; :>> offset = 224; :>> width = 32; :>> point = "CAP_PETAL_ANGLE_03"; }
        attribute f08 : PacketField { :>> order = 8; :>> offset = 256; :>> width = 32; :>> point = "CAP_PETAL_ANGLE_04"; }
        attribute f09 : PacketField { :>> order = 9; :>> offset = 288; :>> width = 16; :>> point = "CAP_CINCH_TENSION_01"; }
        attribute f10 : PacketField { :>> order = 10; :>> offset = 304; :>> width = 16; :>> point = "CAP_CINCH_TENSION_02"; }
        attribute f11 : PacketField { :>> order = 11; :>> offset = 320; :>> width = 8; :>> point = "CAP_LATCH_STATE_01"; }
        attribute f12 : PacketField { :>> order = 12; :>> offset = 328; :>> width = 8; :>> point = "CAP_LATCH_STATE_02"; }
        attribute f13 : PacketField { :>> order = 13; :>> offset = 336; :>> width = 8; :>> point = "CAP_LATCH_STATE_03"; }
        attribute f14 : PacketField { :>> order = 14; :>> offset = 344; :>> width = 8; :>> point = "CAP_LATCH_STATE_04"; }
        attribute f15 : PacketField { :>> order = 15; :>> offset = 352; :>> width = 32; :>> point = "CAP_BODY_SPIN_RATE_01"; }
        attribute f16 : PacketField { :>> order = 16; :>> offset = 384; :>> width = 32; :>> point = "CAP_BODY_SPIN_RATE_02"; }
        attribute f17 : PacketField { :>> order = 17; :>> offset = 416; :>> width = 32; :>> point = "CAP_BODY_SPIN_RATE_03"; }
        attribute f18 : PacketField { :>> order = 18; :>> offset = 448; :>> width = 16; :>> point = "CAP_DESPIN_TORQUE"; }
        attribute f19 : PacketField { :>> order = 19; :>> offset = 464; :>> width = 16; :>> point = "CAP_DESPIN_PROGRESS"; }
        attribute f20 : PacketField { :>> order = 20; :>> offset = 480; :>> width = 8; :>> point = "CAP_CAPTURE_ARMED"; }
        attribute f21 : PacketField { :>> order = 21; :>> offset = 488; :>> width = 8; :>> point = "CAP_CAPTURE_STATE"; }
        attribute f22 : PacketField { :>> order = 22; :>> offset = 496; :>> width = 16; :>> point = "CAP_CONTACT_FORCE_01"; }
        attribute f23 : PacketField { :>> order = 23; :>> offset = 512; :>> width = 16; :>> point = "CAP_CONTACT_FORCE_02"; }
        attribute f24 : PacketField { :>> order = 24; :>> offset = 528; :>> width = 16; :>> point = "CAP_CONTACT_FORCE_03"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item capHkPacket02 : PacketDefinition {
        :>> packetId = 36; :>> mnemonic = "CAP_HK_02"; :>> apid = 193; :>> apidClass = ApidClass::capture;
        :>> source = ApplicationName::captureControl; :>> rate = 1.0 [Hz]; :>> fieldCount = 2; :>> lengthOctets = 20;
        attribute f01 : PacketField { :>> order = 1; :>> offset = 96; :>> width = 32; :>> point = "CAP_BODY_MASS_EST"; }
        attribute f02 : PacketField { :>> order = 2; :>> offset = 128; :>> width = 32; :>> point = "CAP_APPROACH_RATE"; }
        :>> widths = (f01.width, f02.width);
        :>> offsets = (f01.offset, f02.offset);
    }
    item capEngPacket01 : PacketDefinition {
        :>> packetId = 37; :>> mnemonic = "CAP_ENG_01"; :>> apid = 194; :>> apidClass = ApidClass::capture;
        :>> source = ApplicationName::captureControl; :>> rate = 10.0 [Hz]; :>> fieldCount = 24; :>> lengthOctets = 68;
        attribute f01 : PacketField { :>> order = 1; :>> offset = 96; :>> width = 16; :>> point = "CAP_PETAL_MOTOR_I_01"; }
        attribute f02 : PacketField { :>> order = 2; :>> offset = 112; :>> width = 16; :>> point = "CAP_PETAL_MOTOR_I_02"; }
        attribute f03 : PacketField { :>> order = 3; :>> offset = 128; :>> width = 16; :>> point = "CAP_PETAL_MOTOR_I_03"; }
        attribute f04 : PacketField { :>> order = 4; :>> offset = 144; :>> width = 16; :>> point = "CAP_PETAL_MOTOR_I_04"; }
        attribute f05 : PacketField { :>> order = 5; :>> offset = 160; :>> width = 16; :>> point = "CAP_PETAL_T_01"; }
        attribute f06 : PacketField { :>> order = 6; :>> offset = 176; :>> width = 16; :>> point = "CAP_PETAL_T_02"; }
        attribute f07 : PacketField { :>> order = 7; :>> offset = 192; :>> width = 16; :>> point = "CAP_PETAL_T_03"; }
        attribute f08 : PacketField { :>> order = 8; :>> offset = 208; :>> width = 16; :>> point = "CAP_PETAL_T_04"; }
        attribute f09 : PacketField { :>> order = 9; :>> offset = 224; :>> width = 32; :>> point = "CAP_PROX_RANGE_01"; }
        attribute f10 : PacketField { :>> order = 10; :>> offset = 256; :>> width = 32; :>> point = "CAP_PROX_RANGE_02"; }
        attribute f11 : PacketField { :>> order = 11; :>> offset = 288; :>> width = 32; :>> point = "CAP_PROX_RANGE_03"; }
        attribute f12 : PacketField { :>> order = 12; :>> offset = 320; :>> width = 32; :>> point = "CAP_PROX_RANGE_04"; }
        attribute f13 : PacketField { :>> order = 13; :>> offset = 352; :>> width = 32; :>> point = "CAP_PROX_RANGE_05"; }
        attribute f14 : PacketField { :>> order = 14; :>> offset = 384; :>> width = 32; :>> point = "CAP_PROX_RANGE_06"; }
        attribute f15 : PacketField { :>> order = 15; :>> offset = 416; :>> width = 32; :>> point = "CAP_PROX_RANGE_07"; }
        attribute f16 : PacketField { :>> order = 16; :>> offset = 448; :>> width = 32; :>> point = "CAP_PROX_RANGE_08"; }
        attribute f17 : PacketField { :>> order = 17; :>> offset = 480; :>> width = 8; :>> point = "CAP_PROX_STATE_01"; }
        attribute f18 : PacketField { :>> order = 18; :>> offset = 488; :>> width = 8; :>> point = "CAP_PROX_STATE_02"; }
        attribute f19 : PacketField { :>> order = 19; :>> offset = 496; :>> width = 8; :>> point = "CAP_PROX_STATE_03"; }
        attribute f20 : PacketField { :>> order = 20; :>> offset = 504; :>> width = 8; :>> point = "CAP_PROX_STATE_04"; }
        attribute f21 : PacketField { :>> order = 21; :>> offset = 512; :>> width = 8; :>> point = "CAP_PROX_STATE_05"; }
        attribute f22 : PacketField { :>> order = 22; :>> offset = 520; :>> width = 8; :>> point = "CAP_PROX_STATE_06"; }
        attribute f23 : PacketField { :>> order = 23; :>> offset = 528; :>> width = 8; :>> point = "CAP_PROX_STATE_07"; }
        attribute f24 : PacketField { :>> order = 24; :>> offset = 536; :>> width = 8; :>> point = "CAP_PROX_STATE_08"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item capEngPacket02 : PacketDefinition {
        :>> packetId = 38; :>> mnemonic = "CAP_ENG_02"; :>> apid = 195; :>> apidClass = ApidClass::capture;
        :>> source = ApplicationName::captureControl; :>> rate = 0.1 [Hz]; :>> fieldCount = 4; :>> lengthOctets = 20;
        attribute f01 : PacketField { :>> order = 1; :>> offset = 96; :>> width = 16; :>> point = "CAP_MECHANISM_T_01"; }
        attribute f02 : PacketField { :>> order = 2; :>> offset = 112; :>> width = 16; :>> point = "CAP_MECHANISM_T_02"; }
        attribute f03 : PacketField { :>> order = 3; :>> offset = 128; :>> width = 16; :>> point = "CAP_MECHANISM_T_03"; }
        attribute f04 : PacketField { :>> order = 4; :>> offset = 144; :>> width = 16; :>> point = "CAP_MECHANISM_T_04"; }
        :>> widths = (f01.width, f02.width, f03.width, f04.width);
        :>> offsets = (f01.offset, f02.offset, f03.offset, f04.offset);
    }
    item autHkPacket01 : PacketDefinition {
        :>> packetId = 39; :>> mnemonic = "AUT_HK_01"; :>> apid = 68; :>> apidClass = ApidClass::guidance;
        :>> source = ApplicationName::autonomy; :>> rate = 1.0 [Hz]; :>> fieldCount = 19; :>> lengthOctets = 61;
        attribute f01 : PacketField { :>> order = 1; :>> offset = 96; :>> width = 8; :>> point = "AUT_SEQ_STATE_01"; }
        attribute f02 : PacketField { :>> order = 2; :>> offset = 104; :>> width = 8; :>> point = "AUT_SEQ_STATE_02"; }
        attribute f03 : PacketField { :>> order = 3; :>> offset = 112; :>> width = 8; :>> point = "AUT_SEQ_STATE_03"; }
        attribute f04 : PacketField { :>> order = 4; :>> offset = 120; :>> width = 8; :>> point = "AUT_SEQ_STATE_04"; }
        attribute f05 : PacketField { :>> order = 5; :>> offset = 128; :>> width = 32; :>> point = "AUT_SEQ_STEP_01"; }
        attribute f06 : PacketField { :>> order = 6; :>> offset = 160; :>> width = 32; :>> point = "AUT_SEQ_STEP_02"; }
        attribute f07 : PacketField { :>> order = 7; :>> offset = 192; :>> width = 32; :>> point = "AUT_SEQ_STEP_03"; }
        attribute f08 : PacketField { :>> order = 8; :>> offset = 224; :>> width = 32; :>> point = "AUT_SEQ_STEP_04"; }
        attribute f09 : PacketField { :>> order = 9; :>> offset = 256; :>> width = 32; :>> point = "AUT_SEQ_ID_01"; }
        attribute f10 : PacketField { :>> order = 10; :>> offset = 288; :>> width = 32; :>> point = "AUT_SEQ_ID_02"; }
        attribute f11 : PacketField { :>> order = 11; :>> offset = 320; :>> width = 32; :>> point = "AUT_SEQ_ID_03"; }
        attribute f12 : PacketField { :>> order = 12; :>> offset = 352; :>> width = 32; :>> point = "AUT_SEQ_ID_04"; }
        attribute f13 : PacketField { :>> order = 13; :>> offset = 384; :>> width = 32; :>> point = "AUT_WAYPOINT_INDEX"; }
        attribute f14 : PacketField { :>> order = 14; :>> offset = 416; :>> width = 32; :>> point = "AUT_WAYPOINT_RANGE"; }
        attribute f15 : PacketField { :>> order = 15; :>> offset = 448; :>> width = 8; :>> point = "AUT_AUTONOMY_LEVEL"; }
        attribute f16 : PacketField { :>> order = 16; :>> offset = 456; :>> width = 8; :>> point = "AUT_ENGINE_ENABLED_01"; }
        attribute f17 : PacketField { :>> order = 17; :>> offset = 464; :>> width = 8; :>> point = "AUT_ENGINE_ENABLED_02"; }
        attribute f18 : PacketField { :>> order = 18; :>> offset = 472; :>> width = 8; :>> point = "AUT_ENGINE_ENABLED_03"; }
        attribute f19 : PacketField { :>> order = 19; :>> offset = 480; :>> width = 8; :>> point = "AUT_ENGINE_ENABLED_04"; }
        :>> widths = (f01.width, f02.width, f03.width, f04.width, f05.width, f06.width, f07.width, f08.width, f09.width, f10.width, f11.width, f12.width, f13.width, f14.width, f15.width, f16.width, f17.width, f18.width, f19.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset);
    }
    item autEngPacket01 : PacketDefinition {
        :>> packetId = 40; :>> mnemonic = "AUT_ENG_01"; :>> apid = 69; :>> apidClass = ApidClass::guidance;
        :>> source = ApplicationName::autonomy; :>> rate = 1.0 [Hz]; :>> fieldCount = 24; :>> lengthOctets = 96;
        attribute f01 : PacketField { :>> order = 1; :>> offset = 96; :>> width = 32; :>> point = "AUT_SEQ_TIME_TO_NEXT_01"; }
        attribute f02 : PacketField { :>> order = 2; :>> offset = 128; :>> width = 32; :>> point = "AUT_SEQ_TIME_TO_NEXT_02"; }
        attribute f03 : PacketField { :>> order = 3; :>> offset = 160; :>> width = 32; :>> point = "AUT_SEQ_TIME_TO_NEXT_03"; }
        attribute f04 : PacketField { :>> order = 4; :>> offset = 192; :>> width = 32; :>> point = "AUT_SEQ_TIME_TO_NEXT_04"; }
        attribute f05 : PacketField { :>> order = 5; :>> offset = 224; :>> width = 32; :>> point = "AUT_RULE_FIRED_COUNT_01"; }
        attribute f06 : PacketField { :>> order = 6; :>> offset = 256; :>> width = 32; :>> point = "AUT_RULE_FIRED_COUNT_02"; }
        attribute f07 : PacketField { :>> order = 7; :>> offset = 288; :>> width = 32; :>> point = "AUT_RULE_FIRED_COUNT_03"; }
        attribute f08 : PacketField { :>> order = 8; :>> offset = 320; :>> width = 32; :>> point = "AUT_RULE_FIRED_COUNT_04"; }
        attribute f09 : PacketField { :>> order = 9; :>> offset = 352; :>> width = 32; :>> point = "AUT_RULE_FIRED_COUNT_05"; }
        attribute f10 : PacketField { :>> order = 10; :>> offset = 384; :>> width = 32; :>> point = "AUT_RULE_FIRED_COUNT_06"; }
        attribute f11 : PacketField { :>> order = 11; :>> offset = 416; :>> width = 32; :>> point = "AUT_RULE_FIRED_COUNT_07"; }
        attribute f12 : PacketField { :>> order = 12; :>> offset = 448; :>> width = 32; :>> point = "AUT_RULE_FIRED_COUNT_08"; }
        attribute f13 : PacketField { :>> order = 13; :>> offset = 480; :>> width = 32; :>> point = "AUT_RULE_FIRED_COUNT_09"; }
        attribute f14 : PacketField { :>> order = 14; :>> offset = 512; :>> width = 32; :>> point = "AUT_RULE_FIRED_COUNT_10"; }
        attribute f15 : PacketField { :>> order = 15; :>> offset = 544; :>> width = 32; :>> point = "AUT_RULE_FIRED_COUNT_11"; }
        attribute f16 : PacketField { :>> order = 16; :>> offset = 576; :>> width = 32; :>> point = "AUT_RULE_FIRED_COUNT_12"; }
        attribute f17 : PacketField { :>> order = 17; :>> offset = 608; :>> width = 32; :>> point = "AUT_RULE_FIRED_COUNT_13"; }
        attribute f18 : PacketField { :>> order = 18; :>> offset = 640; :>> width = 32; :>> point = "AUT_RULE_FIRED_COUNT_14"; }
        attribute f19 : PacketField { :>> order = 19; :>> offset = 672; :>> width = 32; :>> point = "AUT_RULE_FIRED_COUNT_15"; }
        attribute f20 : PacketField { :>> order = 20; :>> offset = 704; :>> width = 32; :>> point = "AUT_RULE_FIRED_COUNT_16"; }
        attribute f21 : PacketField { :>> order = 21; :>> offset = 736; :>> width = 8; :>> point = "AUT_RULE_ENABLED_01"; }
        attribute f22 : PacketField { :>> order = 22; :>> offset = 744; :>> width = 8; :>> point = "AUT_RULE_ENABLED_02"; }
        attribute f23 : PacketField { :>> order = 23; :>> offset = 752; :>> width = 8; :>> point = "AUT_RULE_ENABLED_03"; }
        attribute f24 : PacketField { :>> order = 24; :>> offset = 760; :>> width = 8; :>> point = "AUT_RULE_ENABLED_04"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item autEngPacket02 : PacketDefinition {
        :>> packetId = 41; :>> mnemonic = "AUT_ENG_02"; :>> apid = 70; :>> apidClass = ApidClass::guidance;
        :>> source = ApplicationName::autonomy; :>> rate = 0.1 [Hz]; :>> fieldCount = 13; :>> lengthOctets = 28;
        attribute f01 : PacketField { :>> order = 1; :>> offset = 96; :>> width = 8; :>> point = "AUT_RULE_ENABLED_05"; }
        attribute f02 : PacketField { :>> order = 2; :>> offset = 104; :>> width = 8; :>> point = "AUT_RULE_ENABLED_06"; }
        attribute f03 : PacketField { :>> order = 3; :>> offset = 112; :>> width = 8; :>> point = "AUT_RULE_ENABLED_07"; }
        attribute f04 : PacketField { :>> order = 4; :>> offset = 120; :>> width = 8; :>> point = "AUT_RULE_ENABLED_08"; }
        attribute f05 : PacketField { :>> order = 5; :>> offset = 128; :>> width = 8; :>> point = "AUT_RULE_ENABLED_09"; }
        attribute f06 : PacketField { :>> order = 6; :>> offset = 136; :>> width = 8; :>> point = "AUT_RULE_ENABLED_10"; }
        attribute f07 : PacketField { :>> order = 7; :>> offset = 144; :>> width = 8; :>> point = "AUT_RULE_ENABLED_11"; }
        attribute f08 : PacketField { :>> order = 8; :>> offset = 152; :>> width = 8; :>> point = "AUT_RULE_ENABLED_12"; }
        attribute f09 : PacketField { :>> order = 9; :>> offset = 160; :>> width = 8; :>> point = "AUT_RULE_ENABLED_13"; }
        attribute f10 : PacketField { :>> order = 10; :>> offset = 168; :>> width = 8; :>> point = "AUT_RULE_ENABLED_14"; }
        attribute f11 : PacketField { :>> order = 11; :>> offset = 176; :>> width = 8; :>> point = "AUT_RULE_ENABLED_15"; }
        attribute f12 : PacketField { :>> order = 12; :>> offset = 184; :>> width = 8; :>> point = "AUT_RULE_ENABLED_16"; }
        attribute f13 : PacketField { :>> order = 13; :>> offset = 192; :>> width = 32; :>> point = "AUT_PLAN_HORIZON"; }
        :>> widths = (f01.width, f02.width, f03.width, f04.width, f05.width, f06.width, f07.width, f08.width, f09.width, f10.width, f11.width, f12.width, f13.width);
        :>> offsets = (f01.offset, f02.offset, f03.offset, f04.offset, f05.offset, f06.offset, f07.offset, f08.offset, f09.offset, f10.offset, f11.offset, f12.offset, f13.offset);
    }
    item fdrHkPacket01 : PacketDefinition {
        :>> packetId = 42; :>> mnemonic = "FDR_HK_01"; :>> apid = 37; :>> apidClass = ApidClass::housekeeping;
        :>> source = ApplicationName::fdir; :>> rate = 1.0 [Hz]; :>> fieldCount = 24; :>> lengthOctets = 36;
        attribute f01 : PacketField { :>> order = 1; :>> offset = 96; :>> width = 8; :>> point = "FDR_MON_STATE_01"; }
        attribute f02 : PacketField { :>> order = 2; :>> offset = 104; :>> width = 8; :>> point = "FDR_MON_STATE_02"; }
        attribute f03 : PacketField { :>> order = 3; :>> offset = 112; :>> width = 8; :>> point = "FDR_MON_STATE_03"; }
        attribute f04 : PacketField { :>> order = 4; :>> offset = 120; :>> width = 8; :>> point = "FDR_MON_STATE_04"; }
        attribute f05 : PacketField { :>> order = 5; :>> offset = 128; :>> width = 8; :>> point = "FDR_MON_STATE_05"; }
        attribute f06 : PacketField { :>> order = 6; :>> offset = 136; :>> width = 8; :>> point = "FDR_MON_STATE_06"; }
        attribute f07 : PacketField { :>> order = 7; :>> offset = 144; :>> width = 8; :>> point = "FDR_MON_STATE_07"; }
        attribute f08 : PacketField { :>> order = 8; :>> offset = 152; :>> width = 8; :>> point = "FDR_MON_STATE_08"; }
        attribute f09 : PacketField { :>> order = 9; :>> offset = 160; :>> width = 8; :>> point = "FDR_MON_STATE_09"; }
        attribute f10 : PacketField { :>> order = 10; :>> offset = 168; :>> width = 8; :>> point = "FDR_MON_STATE_10"; }
        attribute f11 : PacketField { :>> order = 11; :>> offset = 176; :>> width = 8; :>> point = "FDR_MON_STATE_11"; }
        attribute f12 : PacketField { :>> order = 12; :>> offset = 184; :>> width = 8; :>> point = "FDR_MON_STATE_12"; }
        attribute f13 : PacketField { :>> order = 13; :>> offset = 192; :>> width = 8; :>> point = "FDR_MON_STATE_13"; }
        attribute f14 : PacketField { :>> order = 14; :>> offset = 200; :>> width = 8; :>> point = "FDR_MON_STATE_14"; }
        attribute f15 : PacketField { :>> order = 15; :>> offset = 208; :>> width = 8; :>> point = "FDR_MON_STATE_15"; }
        attribute f16 : PacketField { :>> order = 16; :>> offset = 216; :>> width = 8; :>> point = "FDR_MON_STATE_16"; }
        attribute f17 : PacketField { :>> order = 17; :>> offset = 224; :>> width = 8; :>> point = "FDR_MON_STATE_17"; }
        attribute f18 : PacketField { :>> order = 18; :>> offset = 232; :>> width = 8; :>> point = "FDR_MON_STATE_18"; }
        attribute f19 : PacketField { :>> order = 19; :>> offset = 240; :>> width = 8; :>> point = "FDR_MON_STATE_19"; }
        attribute f20 : PacketField { :>> order = 20; :>> offset = 248; :>> width = 8; :>> point = "FDR_MON_STATE_20"; }
        attribute f21 : PacketField { :>> order = 21; :>> offset = 256; :>> width = 8; :>> point = "FDR_MON_STATE_21"; }
        attribute f22 : PacketField { :>> order = 22; :>> offset = 264; :>> width = 8; :>> point = "FDR_MON_STATE_22"; }
        attribute f23 : PacketField { :>> order = 23; :>> offset = 272; :>> width = 8; :>> point = "FDR_MON_STATE_23"; }
        attribute f24 : PacketField { :>> order = 24; :>> offset = 280; :>> width = 8; :>> point = "FDR_MON_STATE_24"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item fdrHkPacket02 : PacketDefinition {
        :>> packetId = 43; :>> mnemonic = "FDR_HK_02"; :>> apid = 38; :>> apidClass = ApidClass::housekeeping;
        :>> source = ApplicationName::fdir; :>> rate = 1.0 [Hz]; :>> fieldCount = 24; :>> lengthOctets = 36;
        attribute f01 : PacketField { :>> order = 1; :>> offset = 96; :>> width = 8; :>> point = "FDR_MON_STATE_25"; }
        attribute f02 : PacketField { :>> order = 2; :>> offset = 104; :>> width = 8; :>> point = "FDR_MON_STATE_26"; }
        attribute f03 : PacketField { :>> order = 3; :>> offset = 112; :>> width = 8; :>> point = "FDR_MON_STATE_27"; }
        attribute f04 : PacketField { :>> order = 4; :>> offset = 120; :>> width = 8; :>> point = "FDR_MON_STATE_28"; }
        attribute f05 : PacketField { :>> order = 5; :>> offset = 128; :>> width = 8; :>> point = "FDR_MON_STATE_29"; }
        attribute f06 : PacketField { :>> order = 6; :>> offset = 136; :>> width = 8; :>> point = "FDR_MON_STATE_30"; }
        attribute f07 : PacketField { :>> order = 7; :>> offset = 144; :>> width = 8; :>> point = "FDR_MON_STATE_31"; }
        attribute f08 : PacketField { :>> order = 8; :>> offset = 152; :>> width = 8; :>> point = "FDR_MON_STATE_32"; }
        attribute f09 : PacketField { :>> order = 9; :>> offset = 160; :>> width = 8; :>> point = "FDR_MON_STATE_33"; }
        attribute f10 : PacketField { :>> order = 10; :>> offset = 168; :>> width = 8; :>> point = "FDR_MON_STATE_34"; }
        attribute f11 : PacketField { :>> order = 11; :>> offset = 176; :>> width = 8; :>> point = "FDR_MON_STATE_35"; }
        attribute f12 : PacketField { :>> order = 12; :>> offset = 184; :>> width = 8; :>> point = "FDR_MON_STATE_36"; }
        attribute f13 : PacketField { :>> order = 13; :>> offset = 192; :>> width = 8; :>> point = "FDR_MON_STATE_37"; }
        attribute f14 : PacketField { :>> order = 14; :>> offset = 200; :>> width = 8; :>> point = "FDR_MON_STATE_38"; }
        attribute f15 : PacketField { :>> order = 15; :>> offset = 208; :>> width = 8; :>> point = "FDR_MON_STATE_39"; }
        attribute f16 : PacketField { :>> order = 16; :>> offset = 216; :>> width = 8; :>> point = "FDR_MON_STATE_40"; }
        attribute f17 : PacketField { :>> order = 17; :>> offset = 224; :>> width = 8; :>> point = "FDR_MON_STATE_41"; }
        attribute f18 : PacketField { :>> order = 18; :>> offset = 232; :>> width = 8; :>> point = "FDR_MON_STATE_42"; }
        attribute f19 : PacketField { :>> order = 19; :>> offset = 240; :>> width = 8; :>> point = "FDR_MON_STATE_43"; }
        attribute f20 : PacketField { :>> order = 20; :>> offset = 248; :>> width = 8; :>> point = "FDR_MON_STATE_44"; }
        attribute f21 : PacketField { :>> order = 21; :>> offset = 256; :>> width = 8; :>> point = "FDR_MON_STATE_45"; }
        attribute f22 : PacketField { :>> order = 22; :>> offset = 264; :>> width = 8; :>> point = "FDR_MON_STATE_46"; }
        attribute f23 : PacketField { :>> order = 23; :>> offset = 272; :>> width = 8; :>> point = "FDR_MON_STATE_47"; }
        attribute f24 : PacketField { :>> order = 24; :>> offset = 280; :>> width = 8; :>> point = "FDR_MON_STATE_48"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item fdrHkPacket03 : PacketDefinition {
        :>> packetId = 44; :>> mnemonic = "FDR_HK_03"; :>> apid = 39; :>> apidClass = ApidClass::housekeeping;
        :>> source = ApplicationName::fdir; :>> rate = 1.0 [Hz]; :>> fieldCount = 10; :>> lengthOctets = 47;
        attribute f01 : PacketField { :>> order = 1; :>> offset = 96; :>> width = 32; :>> point = "FDR_FAULT_COUNT"; }
        attribute f02 : PacketField { :>> order = 2; :>> offset = 128; :>> width = 32; :>> point = "FDR_LAST_FAULT_ID"; }
        attribute f03 : PacketField { :>> order = 3; :>> offset = 160; :>> width = 32; :>> point = "FDR_SAFE_MODE_COUNT"; }
        attribute f04 : PacketField { :>> order = 4; :>> offset = 192; :>> width = 32; :>> point = "FDR_CMD_LOSS_TIMER"; }
        attribute f05 : PacketField { :>> order = 5; :>> offset = 224; :>> width = 32; :>> point = "FDR_RESPONSE_MASK"; }
        attribute f06 : PacketField { :>> order = 6; :>> offset = 256; :>> width = 32; :>> point = "FDR_FLAMEOUT_RETRIES"; }
        attribute f07 : PacketField { :>> order = 7; :>> offset = 288; :>> width = 8; :>> point = "FDR_RESPONSE_STATE"; }
        attribute f08 : PacketField { :>> order = 8; :>> offset = 296; :>> width = 32; :>> point = "FDR_ACTIVE_FAULTS"; }
        attribute f09 : PacketField { :>> order = 9; :>> offset = 328; :>> width = 16; :>> point = "FDR_IMPACT_PROBABILITY"; }
        attribute f10 : PacketField { :>> order = 10; :>> offset = 344; :>> width = 32; :>> point = "FDR_EARTH_RANGE"; }
        :>> widths = (f01.width, f02.width, f03.width, f04.width, f05.width, f06.width, f07.width, f08.width, f09.width, f10.width);
        :>> offsets = (f01.offset, f02.offset, f03.offset, f04.offset, f05.offset, f06.offset, f07.offset, f08.offset, f09.offset, f10.offset);
    }
    item fdrEngPacket01 : PacketDefinition {
        :>> packetId = 45; :>> mnemonic = "FDR_ENG_01"; :>> apid = 40; :>> apidClass = ApidClass::housekeeping;
        :>> source = ApplicationName::fdir; :>> rate = 0.1 [Hz]; :>> fieldCount = 24; :>> lengthOctets = 108;
        attribute f01 : PacketField { :>> order = 1; :>> offset = 96; :>> width = 32; :>> point = "FDR_MON_TRIP_COUNT_01"; }
        attribute f02 : PacketField { :>> order = 2; :>> offset = 128; :>> width = 32; :>> point = "FDR_MON_TRIP_COUNT_02"; }
        attribute f03 : PacketField { :>> order = 3; :>> offset = 160; :>> width = 32; :>> point = "FDR_MON_TRIP_COUNT_03"; }
        attribute f04 : PacketField { :>> order = 4; :>> offset = 192; :>> width = 32; :>> point = "FDR_MON_TRIP_COUNT_04"; }
        attribute f05 : PacketField { :>> order = 5; :>> offset = 224; :>> width = 32; :>> point = "FDR_MON_TRIP_COUNT_05"; }
        attribute f06 : PacketField { :>> order = 6; :>> offset = 256; :>> width = 32; :>> point = "FDR_MON_TRIP_COUNT_06"; }
        attribute f07 : PacketField { :>> order = 7; :>> offset = 288; :>> width = 32; :>> point = "FDR_MON_TRIP_COUNT_07"; }
        attribute f08 : PacketField { :>> order = 8; :>> offset = 320; :>> width = 32; :>> point = "FDR_MON_TRIP_COUNT_08"; }
        attribute f09 : PacketField { :>> order = 9; :>> offset = 352; :>> width = 32; :>> point = "FDR_MON_TRIP_COUNT_09"; }
        attribute f10 : PacketField { :>> order = 10; :>> offset = 384; :>> width = 32; :>> point = "FDR_MON_TRIP_COUNT_10"; }
        attribute f11 : PacketField { :>> order = 11; :>> offset = 416; :>> width = 32; :>> point = "FDR_MON_TRIP_COUNT_11"; }
        attribute f12 : PacketField { :>> order = 12; :>> offset = 448; :>> width = 32; :>> point = "FDR_MON_TRIP_COUNT_12"; }
        attribute f13 : PacketField { :>> order = 13; :>> offset = 480; :>> width = 32; :>> point = "FDR_MON_TRIP_COUNT_13"; }
        attribute f14 : PacketField { :>> order = 14; :>> offset = 512; :>> width = 32; :>> point = "FDR_MON_TRIP_COUNT_14"; }
        attribute f15 : PacketField { :>> order = 15; :>> offset = 544; :>> width = 32; :>> point = "FDR_MON_TRIP_COUNT_15"; }
        attribute f16 : PacketField { :>> order = 16; :>> offset = 576; :>> width = 32; :>> point = "FDR_MON_TRIP_COUNT_16"; }
        attribute f17 : PacketField { :>> order = 17; :>> offset = 608; :>> width = 32; :>> point = "FDR_MON_TRIP_COUNT_17"; }
        attribute f18 : PacketField { :>> order = 18; :>> offset = 640; :>> width = 32; :>> point = "FDR_MON_TRIP_COUNT_18"; }
        attribute f19 : PacketField { :>> order = 19; :>> offset = 672; :>> width = 32; :>> point = "FDR_MON_TRIP_COUNT_19"; }
        attribute f20 : PacketField { :>> order = 20; :>> offset = 704; :>> width = 32; :>> point = "FDR_MON_TRIP_COUNT_20"; }
        attribute f21 : PacketField { :>> order = 21; :>> offset = 736; :>> width = 32; :>> point = "FDR_MON_TRIP_COUNT_21"; }
        attribute f22 : PacketField { :>> order = 22; :>> offset = 768; :>> width = 32; :>> point = "FDR_MON_TRIP_COUNT_22"; }
        attribute f23 : PacketField { :>> order = 23; :>> offset = 800; :>> width = 32; :>> point = "FDR_MON_TRIP_COUNT_23"; }
        attribute f24 : PacketField { :>> order = 24; :>> offset = 832; :>> width = 32; :>> point = "FDR_MON_TRIP_COUNT_24"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item fdrEngPacket02 : PacketDefinition {
        :>> packetId = 46; :>> mnemonic = "FDR_ENG_02"; :>> apid = 41; :>> apidClass = ApidClass::housekeeping;
        :>> source = ApplicationName::fdir; :>> rate = 0.1 [Hz]; :>> fieldCount = 24; :>> lengthOctets = 108;
        attribute f01 : PacketField { :>> order = 1; :>> offset = 96; :>> width = 32; :>> point = "FDR_MON_TRIP_COUNT_25"; }
        attribute f02 : PacketField { :>> order = 2; :>> offset = 128; :>> width = 32; :>> point = "FDR_MON_TRIP_COUNT_26"; }
        attribute f03 : PacketField { :>> order = 3; :>> offset = 160; :>> width = 32; :>> point = "FDR_MON_TRIP_COUNT_27"; }
        attribute f04 : PacketField { :>> order = 4; :>> offset = 192; :>> width = 32; :>> point = "FDR_MON_TRIP_COUNT_28"; }
        attribute f05 : PacketField { :>> order = 5; :>> offset = 224; :>> width = 32; :>> point = "FDR_MON_TRIP_COUNT_29"; }
        attribute f06 : PacketField { :>> order = 6; :>> offset = 256; :>> width = 32; :>> point = "FDR_MON_TRIP_COUNT_30"; }
        attribute f07 : PacketField { :>> order = 7; :>> offset = 288; :>> width = 32; :>> point = "FDR_MON_TRIP_COUNT_31"; }
        attribute f08 : PacketField { :>> order = 8; :>> offset = 320; :>> width = 32; :>> point = "FDR_MON_TRIP_COUNT_32"; }
        attribute f09 : PacketField { :>> order = 9; :>> offset = 352; :>> width = 32; :>> point = "FDR_MON_TRIP_COUNT_33"; }
        attribute f10 : PacketField { :>> order = 10; :>> offset = 384; :>> width = 32; :>> point = "FDR_MON_TRIP_COUNT_34"; }
        attribute f11 : PacketField { :>> order = 11; :>> offset = 416; :>> width = 32; :>> point = "FDR_MON_TRIP_COUNT_35"; }
        attribute f12 : PacketField { :>> order = 12; :>> offset = 448; :>> width = 32; :>> point = "FDR_MON_TRIP_COUNT_36"; }
        attribute f13 : PacketField { :>> order = 13; :>> offset = 480; :>> width = 32; :>> point = "FDR_MON_TRIP_COUNT_37"; }
        attribute f14 : PacketField { :>> order = 14; :>> offset = 512; :>> width = 32; :>> point = "FDR_MON_TRIP_COUNT_38"; }
        attribute f15 : PacketField { :>> order = 15; :>> offset = 544; :>> width = 32; :>> point = "FDR_MON_TRIP_COUNT_39"; }
        attribute f16 : PacketField { :>> order = 16; :>> offset = 576; :>> width = 32; :>> point = "FDR_MON_TRIP_COUNT_40"; }
        attribute f17 : PacketField { :>> order = 17; :>> offset = 608; :>> width = 32; :>> point = "FDR_MON_TRIP_COUNT_41"; }
        attribute f18 : PacketField { :>> order = 18; :>> offset = 640; :>> width = 32; :>> point = "FDR_MON_TRIP_COUNT_42"; }
        attribute f19 : PacketField { :>> order = 19; :>> offset = 672; :>> width = 32; :>> point = "FDR_MON_TRIP_COUNT_43"; }
        attribute f20 : PacketField { :>> order = 20; :>> offset = 704; :>> width = 32; :>> point = "FDR_MON_TRIP_COUNT_44"; }
        attribute f21 : PacketField { :>> order = 21; :>> offset = 736; :>> width = 32; :>> point = "FDR_MON_TRIP_COUNT_45"; }
        attribute f22 : PacketField { :>> order = 22; :>> offset = 768; :>> width = 32; :>> point = "FDR_MON_TRIP_COUNT_46"; }
        attribute f23 : PacketField { :>> order = 23; :>> offset = 800; :>> width = 32; :>> point = "FDR_MON_TRIP_COUNT_47"; }
        attribute f24 : PacketField { :>> order = 24; :>> offset = 832; :>> width = 32; :>> point = "FDR_MON_TRIP_COUNT_48"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item modHkPacket01 : PacketDefinition {
        :>> packetId = 47; :>> mnemonic = "MOD_HK_01"; :>> apid = 42; :>> apidClass = ApidClass::housekeeping;
        :>> source = ApplicationName::modeManagement; :>> rate = 1.0 [Hz]; :>> fieldCount = 20; :>> lengthOctets = 41;
        attribute f01 : PacketField { :>> order = 1; :>> offset = 96; :>> width = 8; :>> point = "MOD_CURRENT_MODE"; }
        attribute f02 : PacketField { :>> order = 2; :>> offset = 104; :>> width = 8; :>> point = "MOD_PREVIOUS_MODE"; }
        attribute f03 : PacketField { :>> order = 3; :>> offset = 112; :>> width = 32; :>> point = "MOD_MODE_TIME"; }
        attribute f04 : PacketField { :>> order = 4; :>> offset = 144; :>> width = 32; :>> point = "MOD_TRANSITION_COUNT"; }
        attribute f05 : PacketField { :>> order = 5; :>> offset = 176; :>> width = 8; :>> point = "MOD_PENDING_MODE"; }
        attribute f06 : PacketField { :>> order = 6; :>> offset = 184; :>> width = 8; :>> point = "MOD_AUTO_TRANSITION_EN"; }
        attribute f07 : PacketField { :>> order = 7; :>> offset = 192; :>> width = 32; :>> point = "MOD_MODE_TABLE_ID"; }
        attribute f08 : PacketField { :>> order = 8; :>> offset = 224; :>> width = 8; :>> point = "MOD_SUBSYSTEM_STATE_01"; }
        attribute f09 : PacketField { :>> order = 9; :>> offset = 232; :>> width = 8; :>> point = "MOD_SUBSYSTEM_STATE_02"; }
        attribute f10 : PacketField { :>> order = 10; :>> offset = 240; :>> width = 8; :>> point = "MOD_SUBSYSTEM_STATE_03"; }
        attribute f11 : PacketField { :>> order = 11; :>> offset = 248; :>> width = 8; :>> point = "MOD_SUBSYSTEM_STATE_04"; }
        attribute f12 : PacketField { :>> order = 12; :>> offset = 256; :>> width = 8; :>> point = "MOD_SUBSYSTEM_STATE_05"; }
        attribute f13 : PacketField { :>> order = 13; :>> offset = 264; :>> width = 8; :>> point = "MOD_SUBSYSTEM_STATE_06"; }
        attribute f14 : PacketField { :>> order = 14; :>> offset = 272; :>> width = 8; :>> point = "MOD_SUBSYSTEM_STATE_07"; }
        attribute f15 : PacketField { :>> order = 15; :>> offset = 280; :>> width = 8; :>> point = "MOD_SUBSYSTEM_STATE_08"; }
        attribute f16 : PacketField { :>> order = 16; :>> offset = 288; :>> width = 8; :>> point = "MOD_SUBSYSTEM_STATE_09"; }
        attribute f17 : PacketField { :>> order = 17; :>> offset = 296; :>> width = 8; :>> point = "MOD_SUBSYSTEM_STATE_10"; }
        attribute f18 : PacketField { :>> order = 18; :>> offset = 304; :>> width = 8; :>> point = "MOD_SUBSYSTEM_STATE_11"; }
        attribute f19 : PacketField { :>> order = 19; :>> offset = 312; :>> width = 8; :>> point = "MOD_SUBSYSTEM_STATE_12"; }
        attribute f20 : PacketField { :>> order = 20; :>> offset = 320; :>> width = 8; :>> point = "MOD_MODE_HOLD"; }
        :>> widths = (f01.width, f02.width, f03.width, f04.width, f05.width, f06.width, f07.width, f08.width, f09.width, f10.width, f11.width, f12.width, f13.width, f14.width, f15.width, f16.width, f17.width, f18.width, f19.width, f20.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset);
    }
    item modEngPacket01 : PacketDefinition {
        :>> packetId = 48; :>> mnemonic = "MOD_ENG_01"; :>> apid = 43; :>> apidClass = ApidClass::housekeeping;
        :>> source = ApplicationName::modeManagement; :>> rate = 0.1 [Hz]; :>> fieldCount = 2; :>> lengthOctets = 20;
        attribute f01 : PacketField { :>> order = 1; :>> offset = 96; :>> width = 32; :>> point = "MOD_MODE_TABLE_CRC"; }
        attribute f02 : PacketField { :>> order = 2; :>> offset = 128; :>> width = 32; :>> point = "MOD_TRANSITION_TIMEOUT"; }
        :>> widths = (f01.width, f02.width);
        :>> offsets = (f01.offset, f02.offset);
    }
    item pbuHkPacket01 : PacketDefinition {
        :>> packetId = 49; :>> mnemonic = "PBU_HK_01"; :>> apid = 44; :>> apidClass = ApidClass::housekeeping;
        :>> source = ApplicationName::parameterBootUpdate; :>> rate = 0.1 [Hz]; :>> fieldCount = 24; :>> lengthOctets = 72;
        attribute f01 : PacketField { :>> order = 1; :>> offset = 96; :>> width = 32; :>> point = "PBU_TABLE_ID_01"; }
        attribute f02 : PacketField { :>> order = 2; :>> offset = 128; :>> width = 32; :>> point = "PBU_TABLE_ID_02"; }
        attribute f03 : PacketField { :>> order = 3; :>> offset = 160; :>> width = 32; :>> point = "PBU_TABLE_ID_03"; }
        attribute f04 : PacketField { :>> order = 4; :>> offset = 192; :>> width = 32; :>> point = "PBU_TABLE_ID_04"; }
        attribute f05 : PacketField { :>> order = 5; :>> offset = 224; :>> width = 32; :>> point = "PBU_TABLE_ID_05"; }
        attribute f06 : PacketField { :>> order = 6; :>> offset = 256; :>> width = 32; :>> point = "PBU_TABLE_ID_06"; }
        attribute f07 : PacketField { :>> order = 7; :>> offset = 288; :>> width = 32; :>> point = "PBU_TABLE_ID_07"; }
        attribute f08 : PacketField { :>> order = 8; :>> offset = 320; :>> width = 32; :>> point = "PBU_TABLE_ID_08"; }
        attribute f09 : PacketField { :>> order = 9; :>> offset = 352; :>> width = 32; :>> point = "PBU_TABLE_ID_09"; }
        attribute f10 : PacketField { :>> order = 10; :>> offset = 384; :>> width = 32; :>> point = "PBU_TABLE_ID_10"; }
        attribute f11 : PacketField { :>> order = 11; :>> offset = 416; :>> width = 32; :>> point = "PBU_TABLE_ID_11"; }
        attribute f12 : PacketField { :>> order = 12; :>> offset = 448; :>> width = 32; :>> point = "PBU_TABLE_ID_12"; }
        attribute f13 : PacketField { :>> order = 13; :>> offset = 480; :>> width = 8; :>> point = "PBU_TABLE_STATE_01"; }
        attribute f14 : PacketField { :>> order = 14; :>> offset = 488; :>> width = 8; :>> point = "PBU_TABLE_STATE_02"; }
        attribute f15 : PacketField { :>> order = 15; :>> offset = 496; :>> width = 8; :>> point = "PBU_TABLE_STATE_03"; }
        attribute f16 : PacketField { :>> order = 16; :>> offset = 504; :>> width = 8; :>> point = "PBU_TABLE_STATE_04"; }
        attribute f17 : PacketField { :>> order = 17; :>> offset = 512; :>> width = 8; :>> point = "PBU_TABLE_STATE_05"; }
        attribute f18 : PacketField { :>> order = 18; :>> offset = 520; :>> width = 8; :>> point = "PBU_TABLE_STATE_06"; }
        attribute f19 : PacketField { :>> order = 19; :>> offset = 528; :>> width = 8; :>> point = "PBU_TABLE_STATE_07"; }
        attribute f20 : PacketField { :>> order = 20; :>> offset = 536; :>> width = 8; :>> point = "PBU_TABLE_STATE_08"; }
        attribute f21 : PacketField { :>> order = 21; :>> offset = 544; :>> width = 8; :>> point = "PBU_TABLE_STATE_09"; }
        attribute f22 : PacketField { :>> order = 22; :>> offset = 552; :>> width = 8; :>> point = "PBU_TABLE_STATE_10"; }
        attribute f23 : PacketField { :>> order = 23; :>> offset = 560; :>> width = 8; :>> point = "PBU_TABLE_STATE_11"; }
        attribute f24 : PacketField { :>> order = 24; :>> offset = 568; :>> width = 8; :>> point = "PBU_TABLE_STATE_12"; }
        :>> widths = (f01.width, f02.width, f03.width, f04.width, f05.width, f06.width, f07.width, f08.width, f09.width, f10.width, f11.width, f12.width, f13.width, f14.width, f15.width, f16.width, f17.width, f18.width, f19.width, f20.width, f21.width, f22.width, f23.width, f24.width);
        :>> offsets = (f01.offset, f02.offset, f03.offset, f04.offset, f05.offset, f06.offset, f07.offset, f08.offset, f09.offset, f10.offset, f11.offset, f12.offset, f13.offset, f14.offset, f15.offset, f16.offset, f17.offset, f18.offset, f19.offset, f20.offset, f21.offset, f22.offset, f23.offset, f24.offset);
    }
    item pbuHkPacket02 : PacketDefinition {
        :>> packetId = 50; :>> mnemonic = "PBU_HK_02"; :>> apid = 45; :>> apidClass = ApidClass::housekeeping;
        :>> source = ApplicationName::parameterBootUpdate; :>> rate = 1.0 [Hz]; :>> fieldCount = 3; :>> lengthOctets = 16;
        attribute f01 : PacketField { :>> order = 1; :>> offset = 96; :>> width = 8; :>> point = "PBU_BOOT_IMAGE_SEL"; }
        attribute f02 : PacketField { :>> order = 2; :>> offset = 104; :>> width = 16; :>> point = "PBU_UPDATE_PROGRESS"; }
        attribute f03 : PacketField { :>> order = 3; :>> offset = 120; :>> width = 8; :>> point = "PBU_UPDATE_STATE"; }
        :>> widths = (f01.width, f02.width, f03.width);
        :>> offsets = (f01.offset, f02.offset, f03.offset);
    }
    item pbuEngPacket01 : PacketDefinition {
        :>> packetId = 51; :>> mnemonic = "PBU_ENG_01"; :>> apid = 46; :>> apidClass = ApidClass::housekeeping;
        :>> source = ApplicationName::parameterBootUpdate; :>> rate = 0.1 [Hz]; :>> fieldCount = 17; :>> lengthOctets = 80;
        attribute f01 : PacketField { :>> order = 1; :>> offset = 96; :>> width = 32; :>> point = "PBU_TABLE_CRC_01"; }
        attribute f02 : PacketField { :>> order = 2; :>> offset = 128; :>> width = 32; :>> point = "PBU_TABLE_CRC_02"; }
        attribute f03 : PacketField { :>> order = 3; :>> offset = 160; :>> width = 32; :>> point = "PBU_TABLE_CRC_03"; }
        attribute f04 : PacketField { :>> order = 4; :>> offset = 192; :>> width = 32; :>> point = "PBU_TABLE_CRC_04"; }
        attribute f05 : PacketField { :>> order = 5; :>> offset = 224; :>> width = 32; :>> point = "PBU_TABLE_CRC_05"; }
        attribute f06 : PacketField { :>> order = 6; :>> offset = 256; :>> width = 32; :>> point = "PBU_TABLE_CRC_06"; }
        attribute f07 : PacketField { :>> order = 7; :>> offset = 288; :>> width = 32; :>> point = "PBU_TABLE_CRC_07"; }
        attribute f08 : PacketField { :>> order = 8; :>> offset = 320; :>> width = 32; :>> point = "PBU_TABLE_CRC_08"; }
        attribute f09 : PacketField { :>> order = 9; :>> offset = 352; :>> width = 32; :>> point = "PBU_TABLE_CRC_09"; }
        attribute f10 : PacketField { :>> order = 10; :>> offset = 384; :>> width = 32; :>> point = "PBU_TABLE_CRC_10"; }
        attribute f11 : PacketField { :>> order = 11; :>> offset = 416; :>> width = 32; :>> point = "PBU_TABLE_CRC_11"; }
        attribute f12 : PacketField { :>> order = 12; :>> offset = 448; :>> width = 32; :>> point = "PBU_TABLE_CRC_12"; }
        attribute f13 : PacketField { :>> order = 13; :>> offset = 480; :>> width = 32; :>> point = "PBU_BOOT_IMAGE_CRC_01"; }
        attribute f14 : PacketField { :>> order = 14; :>> offset = 512; :>> width = 32; :>> point = "PBU_BOOT_IMAGE_CRC_02"; }
        attribute f15 : PacketField { :>> order = 15; :>> offset = 544; :>> width = 32; :>> point = "PBU_PARAM_WRITE_COUNT"; }
        attribute f16 : PacketField { :>> order = 16; :>> offset = 576; :>> width = 32; :>> point = "PBU_PARAM_REJECT_COUNT"; }
        attribute f17 : PacketField { :>> order = 17; :>> offset = 608; :>> width = 32; :>> point = "PBU_EEPROM_WRITE_CYCLES"; }
        :>> widths = (f01.width, f02.width, f03.width, f04.width, f05.width, f06.width, f07.width, f08.width, f09.width, f10.width, f11.width, f12.width, f13.width, f14.width, f15.width, f16.width, f17.width);
        :>> offsets = (f01.offset, f02.offset, f03.offset, f04.offset, f05.offset, f06.offset, f07.offset, f08.offset, f09.offset, f10.offset, f11.offset, f12.offset, f13.offset, f14.offset, f15.offset, f16.offset, f17.offset);
    }

    // ---- parameter and limit tables -------------------------------------------------------
    item cdhParameterTable : FlightParameterTable {
        doc /* Parameter table 1: the flight parameters of the CDH application. */
        :>> tableId = 1; :>> owner = ApplicationName::cdh;
        attribute r1 : ParameterRow { :>> parameterId = 1; :>> name = "watchdogPeriod"; :>> owner = ApplicationName::cdh; :>> value = 5.0; :>> minimum = 0.1; :>> maximum = 30.0; :>> unitSymbol = "s"; }
        attribute r2 : ParameterRow { :>> parameterId = 2; :>> name = "recorderHighWater"; :>> owner = ApplicationName::cdh; :>> value = 0.9; :>> minimum = 0.5; :>> maximum = 0.99; :>> unitSymbol = "1"; }
        attribute r3 : ParameterRow { :>> parameterId = 3; :>> name = "clockSlewLimit"; :>> owner = ApplicationName::cdh; :>> value = 1.0; :>> minimum = 0.01; :>> maximum = 10.0; :>> unitSymbol = "s"; }
        attribute r4 : ParameterRow { :>> parameterId = 4; :>> name = "downlinkQueueDepth"; :>> owner = ApplicationName::cdh; :>> value = 64.0; :>> minimum = 8.0; :>> maximum = 512.0; :>> unitSymbol = "1"; }
        :>> rows = (r1, r2, r3, r4);
    }
    item gncParameterTable : FlightParameterTable {
        doc /* Parameter table 2: the flight parameters of the GNC application. */
        :>> tableId = 2; :>> owner = ApplicationName::gnc;
        attribute r1 : ParameterRow { :>> parameterId = 5; :>> name = "slewRateLimit"; :>> owner = ApplicationName::gnc; :>> value = 0.01; :>> minimum = 0.0001; :>> maximum = 0.02; :>> unitSymbol = "rad/s"; }
        attribute r2 : ParameterRow { :>> parameterId = 6; :>> name = "pointingTolerance"; :>> owner = ApplicationName::gnc; :>> value = 0.001; :>> minimum = 0.0001; :>> maximum = 0.1; :>> unitSymbol = "rad"; }
        attribute r3 : ParameterRow { :>> parameterId = 7; :>> name = "wheelSpeedLimit"; :>> owner = ApplicationName::gnc; :>> value = 600.0; :>> minimum = 100.0; :>> maximum = 650.0; :>> unitSymbol = "rad/s"; }
        attribute r4 : ParameterRow { :>> parameterId = 8; :>> name = "desatThreshold"; :>> owner = ApplicationName::gnc; :>> value = 0.8; :>> minimum = 0.5; :>> maximum = 0.95; :>> unitSymbol = "1"; }
        :>> rows = (r1, r2, r3, r4);
    }
    item sepParameterTable : FlightParameterTable {
        doc /* Parameter table 3: the flight parameters of the SEP application. */
        :>> tableId = 3; :>> owner = ApplicationName::sepControl;
        attribute r1 : ParameterRow { :>> parameterId = 9; :>> name = "throttleMinimum"; :>> owner = ApplicationName::sepControl; :>> value = 0.2; :>> minimum = 0.1; :>> maximum = 0.5; :>> unitSymbol = "1"; }
        attribute r2 : ParameterRow { :>> parameterId = 10; :>> name = "restartDelay"; :>> owner = ApplicationName::sepControl; :>> value = 7200.0; :>> minimum = 60.0; :>> maximum = 86400.0; :>> unitSymbol = "s"; }
        attribute r3 : ParameterRow { :>> parameterId = 11; :>> name = "dischargeTrip"; :>> owner = ApplicationName::sepControl; :>> value = 32.0; :>> minimum = 5.0; :>> maximum = 40.0; :>> unitSymbol = "A"; }
        attribute r4 : ParameterRow { :>> parameterId = 12; :>> name = "tankHeaterSetpoint"; :>> owner = ApplicationName::sepControl; :>> value = 293.0; :>> minimum = 273.0; :>> maximum = 323.0; :>> unitSymbol = "K"; }
        :>> rows = (r1, r2, r3, r4);
    }
    item epsParameterTable : FlightParameterTable {
        doc /* Parameter table 4: the flight parameters of the EPS application. */
        :>> tableId = 4; :>> owner = ApplicationName::powerManagement;
        attribute r1 : ParameterRow { :>> parameterId = 13; :>> name = "endOfChargeVoltage"; :>> owner = ApplicationName::powerManagement; :>> value = 33.0; :>> minimum = 28.0; :>> maximum = 33.6; :>> unitSymbol = "V"; }
        attribute r2 : ParameterRow { :>> parameterId = 14; :>> name = "busLowTrip"; :>> owner = ApplicationName::powerManagement; :>> value = 26.0; :>> minimum = 24.0; :>> maximum = 28.0; :>> unitSymbol = "V"; }
        attribute r3 : ParameterRow { :>> parameterId = 15; :>> name = "busHighTrip"; :>> owner = ApplicationName::powerManagement; :>> value = 30.0; :>> minimum = 28.0; :>> maximum = 32.0; :>> unitSymbol = "V"; }
        attribute r4 : ParameterRow { :>> parameterId = 16; :>> name = "loadShedSoc"; :>> owner = ApplicationName::powerManagement; :>> value = 0.3; :>> minimum = 0.1; :>> maximum = 0.6; :>> unitSymbol = "1"; }
        :>> rows = (r1, r2, r3, r4);
    }
    item thmParameterTable : FlightParameterTable {
        doc /* Parameter table 5: the flight parameters of the THM application. */
        :>> tableId = 5; :>> owner = ApplicationName::thermalControl;
        attribute r1 : ParameterRow { :>> parameterId = 17; :>> name = "deadband"; :>> owner = ApplicationName::thermalControl; :>> value = 2.0; :>> minimum = 0.5; :>> maximum = 10.0; :>> unitSymbol = "K"; }
        attribute r2 : ParameterRow { :>> parameterId = 18; :>> name = "survivalLow"; :>> owner = ApplicationName::thermalControl; :>> value = 243.0; :>> minimum = 233.0; :>> maximum = 283.0; :>> unitSymbol = "K"; }
        attribute r3 : ParameterRow { :>> parameterId = 19; :>> name = "survivalHigh"; :>> owner = ApplicationName::thermalControl; :>> value = 253.0; :>> minimum = 243.0; :>> maximum = 293.0; :>> unitSymbol = "K"; }
        attribute r4 : ParameterRow { :>> parameterId = 20; :>> name = "heaterPowerCap"; :>> owner = ApplicationName::thermalControl; :>> value = 800.0; :>> minimum = 50.0; :>> maximum = 900.0; :>> unitSymbol = "W"; }
        :>> rows = (r1, r2, r3, r4);
    }
    item comParameterTable : FlightParameterTable {
        doc /* Parameter table 6: the flight parameters of the COM application. */
        :>> tableId = 6; :>> owner = ApplicationName::telecom;
        attribute r1 : ParameterRow { :>> parameterId = 21; :>> name = "defaultDownlinkRate"; :>> owner = ApplicationName::telecom; :>> value = 2000000.0; :>> minimum = 10.0; :>> maximum = 4000000.0; :>> unitSymbol = "Hz"; }
        attribute r2 : ParameterRow { :>> parameterId = 22; :>> name = "defaultUplinkRate"; :>> owner = ApplicationName::telecom; :>> value = 2000.0; :>> minimum = 7.8125; :>> maximum = 4000.0; :>> unitSymbol = "Hz"; }
        attribute r3 : ParameterRow { :>> parameterId = 23; :>> name = "hgaSlewLimit"; :>> owner = ApplicationName::telecom; :>> value = 0.005; :>> minimum = 0.0001; :>> maximum = 0.02; :>> unitSymbol = "rad/s"; }
        attribute r4 : ParameterRow { :>> parameterId = 24; :>> name = "transmitPower"; :>> owner = ApplicationName::telecom; :>> value = 60.0; :>> minimum = 5.0; :>> maximum = 100.0; :>> unitSymbol = "W"; }
        :>> rows = (r1, r2, r3, r4);
    }
    item insParameterTable : FlightParameterTable {
        doc /* Parameter table 7: the flight parameters of the INS application. */
        :>> tableId = 7; :>> owner = ApplicationName::inspectorHandling;
        attribute r1 : ParameterRow { :>> parameterId = 25; :>> name = "releaseSpeed"; :>> owner = ApplicationName::inspectorHandling; :>> value = 0.05; :>> minimum = 0.02; :>> maximum = 0.2; :>> unitSymbol = "m/s"; }
        attribute r2 : ParameterRow { :>> parameterId = 26; :>> name = "imagingCadence"; :>> owner = ApplicationName::inspectorHandling; :>> value = 10.0; :>> minimum = 1.0; :>> maximum = 600.0; :>> unitSymbol = "s"; }
        attribute r3 : ParameterRow { :>> parameterId = 27; :>> name = "relayRate"; :>> owner = ApplicationName::inspectorHandling; :>> value = 1000000.0; :>> minimum = 1000.0; :>> maximum = 2000000.0; :>> unitSymbol = "Hz"; }
        attribute r4 : ParameterRow { :>> parameterId = 28; :>> name = "contactTimeout"; :>> owner = ApplicationName::inspectorHandling; :>> value = 7200.0; :>> minimum = 600.0; :>> maximum = 86400.0; :>> unitSymbol = "s"; }
        :>> rows = (r1, r2, r3, r4);
    }
    item capParameterTable : FlightParameterTable {
        doc /* Parameter table 8: the flight parameters of the CAP application. */
        :>> tableId = 8; :>> owner = ApplicationName::captureControl;
        attribute r1 : ParameterRow { :>> parameterId = 29; :>> name = "approachRateLimit"; :>> owner = ApplicationName::captureControl; :>> value = 0.1; :>> minimum = 0.01; :>> maximum = 0.5; :>> unitSymbol = "m/s"; }
        attribute r2 : ParameterRow { :>> parameterId = 30; :>> name = "contactForceLimit"; :>> owner = ApplicationName::captureControl; :>> value = 200.0; :>> minimum = 1.0; :>> maximum = 500.0; :>> unitSymbol = "N"; }
        attribute r3 : ParameterRow { :>> parameterId = 31; :>> name = "cinchTension"; :>> owner = ApplicationName::captureControl; :>> value = 1000.0; :>> minimum = 10.0; :>> maximum = 2000.0; :>> unitSymbol = "N"; }
        attribute r4 : ParameterRow { :>> parameterId = 32; :>> name = "despinTorqueLimit"; :>> owner = ApplicationName::captureControl; :>> value = 0.5; :>> minimum = 0.0; :>> maximum = 1.0; :>> unitSymbol = "1"; }
        :>> rows = (r1, r2, r3, r4);
    }
    item autParameterTable : FlightParameterTable {
        doc /* Parameter table 9: the flight parameters of the AUT application. */
        :>> tableId = 9; :>> owner = ApplicationName::autonomy;
        attribute r1 : ParameterRow { :>> parameterId = 33; :>> name = "planHorizon"; :>> owner = ApplicationName::autonomy; :>> value = 86400.0; :>> minimum = 3600.0; :>> maximum = 604800.0; :>> unitSymbol = "s"; }
        attribute r2 : ParameterRow { :>> parameterId = 34; :>> name = "autonomyLevel"; :>> owner = ApplicationName::autonomy; :>> value = 1.0; :>> minimum = 0.0; :>> maximum = 3.0; :>> unitSymbol = "1"; }
        attribute r3 : ParameterRow { :>> parameterId = 35; :>> name = "waypointHoldDefault"; :>> owner = ApplicationName::autonomy; :>> value = 600.0; :>> minimum = 0.0; :>> maximum = 86400.0; :>> unitSymbol = "s"; }
        attribute r4 : ParameterRow { :>> parameterId = 36; :>> name = "ruleCooldown"; :>> owner = ApplicationName::autonomy; :>> value = 60.0; :>> minimum = 1.0; :>> maximum = 3600.0; :>> unitSymbol = "s"; }
        :>> rows = (r1, r2, r3, r4);
    }
    item fdrParameterTable : FlightParameterTable {
        doc /* Parameter table 10: the flight parameters of the FDR application. */
        :>> tableId = 10; :>> owner = ApplicationName::fdir;
        attribute r1 : ParameterRow { :>> parameterId = 37; :>> name = "commandLossTimeout"; :>> owner = ApplicationName::fdir; :>> value = 604800.0; :>> minimum = 3600.0; :>> maximum = 2592000.0; :>> unitSymbol = "s"; }
        attribute r2 : ParameterRow { :>> parameterId = 38; :>> name = "flameoutRetries"; :>> owner = ApplicationName::fdir; :>> value = 2.0; :>> minimum = 0.0; :>> maximum = 5.0; :>> unitSymbol = "1"; }
        attribute r3 : ParameterRow { :>> parameterId = 39; :>> name = "batteryLowFraction"; :>> owner = ApplicationName::fdir; :>> value = 0.3; :>> minimum = 0.1; :>> maximum = 0.6; :>> unitSymbol = "1"; }
        attribute r4 : ParameterRow { :>> parameterId = 40; :>> name = "impactProbabilityLimit"; :>> owner = ApplicationName::fdir; :>> value = 0.0001; :>> minimum = 1e-07; :>> maximum = 0.001; :>> unitSymbol = "1"; }
        :>> rows = (r1, r2, r3, r4);
    }
    item modParameterTable : FlightParameterTable {
        doc /* Parameter table 11: the flight parameters of the MOD application. */
        :>> tableId = 11; :>> owner = ApplicationName::modeManagement;
        attribute r1 : ParameterRow { :>> parameterId = 41; :>> name = "transitionTimeout"; :>> owner = ApplicationName::modeManagement; :>> value = 300.0; :>> minimum = 1.0; :>> maximum = 3600.0; :>> unitSymbol = "s"; }
        attribute r2 : ParameterRow { :>> parameterId = 42; :>> name = "twoStepWindow"; :>> owner = ApplicationName::modeManagement; :>> value = 600.0; :>> minimum = 10.0; :>> maximum = 3600.0; :>> unitSymbol = "s"; }
        attribute r3 : ParameterRow { :>> parameterId = 43; :>> name = "modeTableId"; :>> owner = ApplicationName::modeManagement; :>> value = 11.0; :>> minimum = 0.0; :>> maximum = 11.0; :>> unitSymbol = "1"; }
        attribute r4 : ParameterRow { :>> parameterId = 44; :>> name = "autoTransitionDefault"; :>> owner = ApplicationName::modeManagement; :>> value = 1.0; :>> minimum = 0.0; :>> maximum = 1.0; :>> unitSymbol = "1"; }
        :>> rows = (r1, r2, r3, r4);
    }
    item pbuParameterTable : FlightParameterTable {
        doc /* Parameter table 12: the flight parameters of the PBU application. */
        :>> tableId = 12; :>> owner = ApplicationName::parameterBootUpdate;
        attribute r1 : ParameterRow { :>> parameterId = 45; :>> name = "stagingBufferSize"; :>> owner = ApplicationName::parameterBootUpdate; :>> value = 65536.0; :>> minimum = 4096.0; :>> maximum = 65536.0; :>> unitSymbol = "1"; }
        attribute r2 : ParameterRow { :>> parameterId = 46; :>> name = "bootRetryLimit"; :>> owner = ApplicationName::parameterBootUpdate; :>> value = 3.0; :>> minimum = 1.0; :>> maximum = 5.0; :>> unitSymbol = "1"; }
        attribute r3 : ParameterRow { :>> parameterId = 47; :>> name = "eepromCycleLimit"; :>> owner = ApplicationName::parameterBootUpdate; :>> value = 100000.0; :>> minimum = 1000.0; :>> maximum = 100000.0; :>> unitSymbol = "1"; }
        attribute r4 : ParameterRow { :>> parameterId = 48; :>> name = "tableCount"; :>> owner = ApplicationName::parameterBootUpdate; :>> value = 12.0; :>> minimum = 1.0; :>> maximum = 12.0; :>> unitSymbol = "1"; }
        :>> rows = (r1, r2, r3, r4);
    }
    attribute flightLimitTable : FdirLimitTable {
        doc /* The flight limit table: the six thresholds the fault supervisor's cruise limits read, one row each. */
        :>> tableId = 13;
        :>> commandLossTimeout = 7.0 [d];
        :>> thrusterRestartDelay = 2.0 [h];
        :>> maximumFlameoutRetries = 2;
        :>> batteryLowFraction = 0.30;
        :>> earthExclusionRadius = 63781.37 [km];
        :>> maximumImpactProbability = 1.0e-4;
    }
    attribute tableLimits : MonitorLimits {
        doc /* The supervisor's limit set as read from the limit table: every threshold is a table row. */
        :>> commandLossTimeout = flightLimitTable.commandLossTimeout;
        :>> thrusterRestartDelay = flightLimitTable.thrusterRestartDelay;
        :>> maximumFlameoutRetries = flightLimitTable.maximumFlameoutRetries;
        :>> batteryLowFraction = flightLimitTable.batteryLowFraction;
        :>> earthExclusionRadius = flightLimitTable.earthExclusionRadius;
        :>> maximumImpactProbability = flightLimitTable.maximumImpactProbability;
    }
    attribute flightApids : ApidTable {
        doc /* The APID class bases of the flight dictionary: each class's packets are numbered upward from its base. */
        :>> housekeeping = 16;
        :>> guidance = 64;
        :>> propulsion = 128;
        :>> capture = 192;
        :>> relay = 256;
        :>> imaging = 320;
    }

    // ---- the dictionary and its consistency checks ----------------------------------------
    part def FlightDictionary :> Dictionary {
        doc /* The flight dictionary: the rows above collected, with the counts and the consistency flags the dictionary requirement reads computed from them. The opcode, mnemonic, APID and event id sequences are unique features, so a repeated value fails their evaluation. */
        item commands : CommandDefinition[*];
        item telemetryPoints : TelemetryPointDefinition[*];
        item events : EventDefinition[*];
        item packets : PacketDefinition[*];
        item parameterTables : FlightParameterTable[*];
        attribute limitTable : FdirLimitTable;
        attribute commandApids : Natural[*];
        attribute opcodeNumbers : Natural[*] = commands.opcodeNumber;
        attribute commandMnemonics : String[*] = commands.mnemonic;
        attribute telemetryMnemonics : String[*] = telemetryPoints.mnemonic;
        attribute eventIds : Natural[*] = events.eventId;
        attribute packetApids : Natural[*] = packets.apid;
        attribute apidsAllocated : Natural[*] = (packetApids, commandApids);
        attribute :>> commandCount = size(commands);
        attribute :>> telemetryPointCount = size(telemetryPoints);
        attribute :>> eventCount = size(events);
        attribute :>> packetCount = size(packets);
        attribute :>> opcodesUnique = size(opcodeNumbers) == commandCount;
        attribute :>> mnemonicsUnique = size(commandMnemonics) == commandCount and size(telemetryMnemonics) == telemetryPointCount;
        attribute :>> apidsUnique = size(apidsAllocated) == packetCount + size(commandApids);
        attribute :>> apidsWithinRange = apidsAllocated->forAll { in a : Natural; a <= apidMaximum };
        attribute :>> eventIdsUnique = size(eventIds) == eventCount;
        attribute :>> packetsSumToLength = packets->forAll { in p : PacketDefinition; p.layoutConsistent };
        attribute :>> commandsHaveModePrecondition = commands->forAll { in c : CommandDefinition; c.opcodeNumber != null and notEmpty(c.allowedModes) and includes(commandApids, c.apid) };
        attribute :>> pointsHaveSource = telemetryPoints->forAll { in t : TelemetryPointDefinition; t.source != null };
        attribute :>> parametersInRange = parameterTables->forAll { in t : FlightParameterTable; t.allInRange };
        attribute :>> fdirThresholdsReadLimitTable = cruiseLimits.commandLossTimeout == limitTable.commandLossTimeout
            and cruiseLimits.thrusterRestartDelay == limitTable.thrusterRestartDelay
            and cruiseLimits.maximumFlameoutRetries == limitTable.maximumFlameoutRetries
            and cruiseLimits.batteryLowFraction == limitTable.batteryLowFraction
            and cruiseLimits.earthExclusionRadius == limitTable.earthExclusionRadius
            and cruiseLimits.maximumImpactProbability == limitTable.maximumImpactProbability;
        attribute hazardousCommandCount : Natural = size(commands->select { in c : CommandDefinition; c.hazardous });
        attribute housekeepingPointCount : Natural = size(telemetryPoints->select { in t : TelemetryPointDefinition; t.kind == TelemetryKind::housekeeping });
        attribute faultEventCount : Natural = size(events->select { in e : EventDefinition; e.fdirRelevant });
        attribute abortOpcode : Opcode = Opcode::FDR_ABORT_TO_RETREAT;
        attribute abortIsHazardous : Boolean = commands->exists { in c : CommandDefinition; c.opcodeLiteral == abortOpcode and c.hazardous };
    }
    part flightDictionary : FlightDictionary {
        doc /* The Tethys flight dictionary at its current issue. */
        :>> apids = flightApids;
        :>> limitTable = flightLimitTable;
        :>> commandApids = (960, 961, 962, 963, 964, 965, 966, 967, 968, 969, 970, 971);
        :>> commands = (
            cdhNoop, cdhResetProcessor, cdhSelectPrimeComputer, cdhSetClock, cdhAdjustClock, cdhDumpMemory,
            cdhLoadMemory, cdhStartRecording, cdhStopRecording, cdhDownlinkFile, cdhDeleteFile,
            cdhSetDownlinkPriority, cdhSetWatchdogPeriod, cdhClearCounters, cdhSetAppRateCdh,
            cdhSetAppRateGnc, cdhSetAppRateSep, cdhSetAppRateEps, cdhSetAppRateThm, cdhSetAppRateCom,
            cdhSetAppRateIns, cdhSetAppRateCap, cdhSetAppRateAut, cdhSetAppRateFdr, cdhSetAppRateMod,
            cdhSetAppRatePbu, gncSetAttitudeTarget, gncSetRateTarget, gncSlewTo, gncHoldAttitude,
            gncSelectStarTracker, gncSelectImu, gncDesaturateWheels, gncSetWheelSpeed, gncEnableRcsControl,
            gncDisableRcsControl, gncUploadEphemeris, gncSetGuidanceMode, gncStartTcm, gncAbortTcm,
            gncSetPointingTolerance, gncResetEstimator, gncRcsThrusterEnable01, gncRcsThrusterDisable01,
            gncRcsThrusterEnable02, gncRcsThrusterDisable02, gncRcsThrusterEnable03, gncRcsThrusterDisable03,
            gncRcsThrusterEnable04, gncRcsThrusterDisable04, gncRcsThrusterEnable05, gncRcsThrusterDisable05,
            gncRcsThrusterEnable06, gncRcsThrusterDisable06, gncRcsThrusterEnable07, gncRcsThrusterDisable07,
            gncRcsThrusterEnable08, gncRcsThrusterDisable08, gncWheelOn1, gncWheelOff1, gncWheelOn2,
            gncWheelOff2, gncWheelOn3, gncWheelOff3, gncWheelOn4, gncWheelOff4, sepStartThrustArc,
            sepStopThrust, sepSetThrottle, sepSelectThruster, sepPrimeFeed, sepVentFeed, sepSetFlowRate,
            sepThrusterRestart, sepOpenLatchValve, sepCloseLatchValve, sepGimbalSet, sepGimbalHome,
            sepSetDischargeLimit, sepTankHeaterSetpoint, sepPpuOn1, sepPpuOff1, sepPpuOn2, sepPpuOff2,
            sepPpuOn3, sepPpuOff3, sepCathodeHeaterOn1, sepCathodeHeaterOff1, sepCathodeHeaterOn2,
            sepCathodeHeaterOff2, sepCathodeHeaterOn3, sepCathodeHeaterOff3, epsSetBatteryChargeLimit,
            epsSetLoadShedLevel, epsSelectBattery, epsSadaSetAngle, epsSadaTrackSun, epsSadaHold,
            epsSetBusVoltageLimits, epsBalanceCells, epsResetSwitchTrips, epsSetArrayStringMask,
            epsSwitchOn01, epsSwitchOff01, epsSwitchOn02, epsSwitchOff02, epsSwitchOn03, epsSwitchOff03,
            epsSwitchOn04, epsSwitchOff04, epsSwitchOn05, epsSwitchOff05, epsSwitchOn06, epsSwitchOff06,
            epsSwitchOn07, epsSwitchOff07, epsSwitchOn08, epsSwitchOff08, epsSwitchOn09, epsSwitchOff09,
            epsSwitchOn10, epsSwitchOff10, epsSwitchOn11, epsSwitchOff11, epsSwitchOn12, epsSwitchOff12,
            epsSwitchOn13, epsSwitchOff13, epsSwitchOn14, epsSwitchOff14, epsSwitchOn15, epsSwitchOff15,
            epsSwitchOn16, epsSwitchOff16, epsSwitchOn17, epsSwitchOff17, epsSwitchOn18, epsSwitchOff18,
            epsSwitchOn19, epsSwitchOff19, epsSwitchOn20, epsSwitchOff20, epsSwitchOn21, epsSwitchOff21,
            epsSwitchOn22, epsSwitchOff22, epsSwitchOn23, epsSwitchOff23, epsSwitchOn24, epsSwitchOff24,
            thmSetControlMode, thmLouverSet, thmLouverAuto, thmSetSurvivalSetpoints, thmSetDeadband,
            thmEnableAllHeaters, thmDisableAllHeaters, thmSetHeaterPowerCap, thmHeaterEnable01,
            thmHeaterDisable01, thmHeaterEnable02, thmHeaterDisable02, thmHeaterEnable03, thmHeaterDisable03,
            thmHeaterEnable04, thmHeaterDisable04, thmHeaterEnable05, thmHeaterDisable05, thmHeaterEnable06,
            thmHeaterDisable06, thmHeaterEnable07, thmHeaterDisable07, thmHeaterEnable08, thmHeaterDisable08,
            thmHeaterEnable09, thmHeaterDisable09, thmHeaterEnable10, thmHeaterDisable10, thmHeaterEnable11,
            thmHeaterDisable11, thmHeaterEnable12, thmHeaterDisable12, thmHeaterEnable13, thmHeaterDisable13,
            thmHeaterEnable14, thmHeaterDisable14, thmHeaterEnable15, thmHeaterDisable15, thmHeaterEnable16,
            thmHeaterDisable16, thmHeaterSetpoint01, thmHeaterSetpoint02, thmHeaterSetpoint03,
            thmHeaterSetpoint04, thmHeaterSetpoint05, thmHeaterSetpoint06, thmHeaterSetpoint07,
            thmHeaterSetpoint08, thmHeaterSetpoint09, thmHeaterSetpoint10, thmHeaterSetpoint11,
            thmHeaterSetpoint12, thmHeaterSetpoint13, thmHeaterSetpoint14, thmHeaterSetpoint15,
            thmHeaterSetpoint16, comTransmitterOn, comTransmitterOff, comSelectTransponder, comSelectAntenna,
            comSetDownlinkRate, comSetUplinkRate, comRangingOn, comRangingOff, comHgaPoint, comHgaTrackEarth,
            comHgaStow, comSetPassWindow, comSetCoding, comSetTransmitPower, comDownlinkRatePreset1,
            comDownlinkRatePreset2, comDownlinkRatePreset3, comDownlinkRatePreset4, comDownlinkRatePreset5,
            comDownlinkRatePreset6, insArmRelease, insSafeRelease, insReleaseInspector, insForwardCommand,
            insStartImagingSession, insStopImagingSession, insSetImageCompression, insSelectRelayRate,
            insStoreImageSegment, insDownlinkImage, insRetireInspector, insSetRelayWindow, insEnableRelay,
            insDisableRelay, capArmCapture, capDisarmCapture, capDeployBag, capCloseBag, capCinchBag,
            capStartDespin, capStopDespin, capSetDespinTorque, capLatchBody, capReleaseBody, capAbortCapture,
            capSetApproachRate, capEnableProximitySensors, capDisableProximitySensors,
            capSetContactForceLimit, capSetBodyMassEstimate, capPetalOpen1, capPetalClose1, capPetalOpen2,
            capPetalClose2, capPetalOpen3, capPetalClose3, capPetalOpen4, capPetalClose4, autLoadSequence,
            autStartSequence, autStopSequence, autPauseSequence, autResumeSequence, autSetSequenceParameter,
            autEnableAutonomy, autDisableAutonomy, autSetRuleEnable, autClearRuleHistory, autSetWaypoint,
            autClearWaypoints, autSetPlanHorizon, autEngineEnable1, autEngineDisable1, autEngineEnable2,
            autEngineDisable2, autEngineEnable3, autEngineDisable3, autEngineEnable4, autEngineDisable4,
            fdrEnableMonitor, fdrDisableMonitor, fdrSetLimit, fdrResetLimit, fdrClearFault,
            fdrAcknowledgeFault, fdrMaskResponse, fdrUnmaskResponse, fdrForceSafeMode,
            fdrSetCommandLossTimer, fdrResetCommandLossTimer, fdrAbortToRetreat, fdrSetFlameoutRetries,
            fdrSetBatteryLowFraction, fdrSetImpactProbabilityLimit, fdrSetExclusionRadius,
            fdrMonitorResponse01, fdrMonitorResponse02, fdrMonitorResponse03, fdrMonitorResponse04,
            fdrMonitorResponse05, fdrMonitorResponse06, fdrMonitorResponse07, fdrMonitorResponse08,
            fdrMonitorResponse09, fdrMonitorResponse10, fdrMonitorResponse11, fdrMonitorResponse12,
            modSetMode, modConfirmMode, modCancelPendingMode, modLoadModeTable, modEnableAutoTransition,
            modDisableAutoTransition, modHoldMode, modResumeMode, modSetTransitionTimeout, pbuLoadTable,
            pbuDumpTable, pbuActivateTable, pbuVerifyTable, pbuSetParameter, pbuGetParameter,
            pbuStartBootUpdate, pbuAbortBootUpdate, pbuSelectBootImage, pbuCommitBootImage, pbuTableReset01,
            pbuTableReset02, pbuTableReset03, pbuTableReset04, pbuTableReset05, pbuTableReset06,
            pbuTableReset07, pbuTableReset08, pbuTableReset09, pbuTableReset10, pbuTableReset11,
            pbuTableReset12);
        :>> telemetryPoints = (
            cdhTBoard01, cdhTBoard02, cdhTBoard03, cdhTBoard04, cdhCpuLoad01, cdhCpuLoad02, cdhMemUsed01,
            cdhMemUsed02, cdhRecorderFill, cdhUptime, cdhCmdAcceptCount, cdhCmdRejectCount, cdhBusMsgRate,
            cdhFileCount, cdhClockCoarse, cdhClockFine, cdhAppRate01, cdhAppRate02, cdhAppRate03,
            cdhAppRate04, cdhAppRate05, cdhAppRate06, cdhAppRate07, cdhAppRate08, cdhAppRate09, cdhAppRate10,
            cdhAppRate11, cdhAppRate12, cdhAppLoad01, cdhAppLoad02, cdhAppLoad03, cdhAppLoad04, cdhAppLoad05,
            cdhAppLoad06, cdhAppLoad07, cdhAppLoad08, cdhAppLoad09, cdhAppLoad10, cdhAppLoad11, cdhAppLoad12,
            cdhPartitionStatus01, cdhPartitionStatus02, cdhPartitionStatus03, cdhPartitionStatus04,
            cdhBusRtErrors01, cdhBusRtErrors02, cdhBusRtErrors03, cdhBusRtErrors04, cdhBusRtErrors05,
            cdhBusRtErrors06, cdhBusRtErrors07, cdhBusRtErrors08, cdhBusRtErrors09, cdhBusRtErrors10,
            cdhBusRtErrors11, cdhBusRtErrors12, cdhBusRtErrors13, cdhBusRtErrors14, cdhBusRtErrors15,
            cdhBusRtErrors16, cdhWatchdogMargin, gncQ01, gncQ02, gncQ03, gncQ04, gncRate01, gncRate02,
            gncRate03, gncAttErr01, gncAttErr02, gncAttErr03, gncRateErr01, gncRateErr02, gncRateErr03,
            gncStT01, gncStT02, gncStStatus01, gncStStatus02, gncImuGyro01, gncImuGyro02, gncImuGyro03,
            gncImuGyro04, gncImuGyro05, gncImuGyro06, gncImuAccel01, gncImuAccel02, gncImuAccel03,
            gncImuAccel04, gncImuAccel05, gncImuAccel06, gncImuT01, gncImuT02, gncWheelSpeed01,
            gncWheelSpeed02, gncWheelSpeed03, gncWheelSpeed04, gncWheelI01, gncWheelI02, gncWheelI03,
            gncWheelI04, gncWheelT01, gncWheelT02, gncWheelT03, gncWheelT04, gncRcsOnTime01, gncRcsOnTime02,
            gncRcsOnTime03, gncRcsOnTime04, gncRcsOnTime05, gncRcsOnTime06, gncRcsOnTime07, gncRcsOnTime08,
            gncRcsPulses01, gncRcsPulses02, gncRcsPulses03, gncRcsPulses04, gncRcsPulses05, gncRcsPulses06,
            gncRcsPulses07, gncRcsPulses08, gncSunSensor01, gncSunSensor02, gncSunSensor03, gncSunSensor04,
            gncSunSensor05, gncSunSensor06, gncRangeToTarget, gncRangeRate, gncBearing01, gncBearing02,
            gncEphemerisAge, gncGuidanceMode, gncMomentum01, gncMomentum02, gncMomentum03, sepDischargeI01,
            sepDischargeI02, sepDischargeI03, sepDischargeV01, sepDischargeV02, sepDischargeV03,
            sepAnodeFlow01, sepAnodeFlow02, sepAnodeFlow03, sepCathodeFlow01, sepCathodeFlow02,
            sepCathodeFlow03, sepKeeperI01, sepKeeperI02, sepKeeperI03, sepMagnetI01, sepMagnetI02,
            sepMagnetI03, sepCathodeHtrI01, sepCathodeHtrI02, sepCathodeHtrI03, sepThrusterT01,
            sepThrusterT02, sepThrusterT03, sepPpuInPower01, sepPpuInPower02, sepPpuInPower03, sepPpuT01,
            sepPpuT02, sepPpuT03, sepPpuStatus01, sepPpuStatus02, sepPpuStatus03, sepPpuEfficiency01,
            sepPpuEfficiency02, sepPpuEfficiency03, sepTankP01, sepTankP02, sepTankT01, sepTankT02,
            sepXenonRemaining, sepFlowTotal, sepRegP01, sepRegP02, sepLatchValve01, sepLatchValve02,
            sepLatchValve03, sepLatchValve04, sepLatchValve05, sepLatchValve06, sepGimbalAngle01,
            sepGimbalAngle02, sepGimbalAngle03, sepGimbalAngle04, sepGimbalAngle05, sepGimbalAngle06,
            sepThrustEst, sepIspEst, sepArcElapsed, sepArcRemaining, epsBattCellV01, epsBattCellV02,
            epsBattCellV03, epsBattCellV04, epsBattCellV05, epsBattCellV06, epsBattCellV07, epsBattCellV08,
            epsBattCellV09, epsBattCellV10, epsBattCellV11, epsBattCellV12, epsBattCellV13, epsBattCellV14,
            epsBattCellV15, epsBattCellV16, epsBattCellV17, epsBattCellV18, epsBattCellV19, epsBattCellV20,
            epsBattCellV21, epsBattCellV22, epsBattCellV23, epsBattCellV24, epsBattCellV25, epsBattCellV26,
            epsBattCellV27, epsBattCellV28, epsBattCellV29, epsBattCellV30, epsBattCellV31, epsBattCellV32,
            epsBattT01, epsBattT02, epsBattT03, epsBattT04, epsBattSoc01, epsBattSoc02, epsBattI01,
            epsBattI02, epsArrayStringI01, epsArrayStringI02, epsArrayStringI03, epsArrayStringI04,
            epsArrayStringI05, epsArrayStringI06, epsArrayStringI07, epsArrayStringI08, epsArrayStringI09,
            epsArrayStringI10, epsArrayStringI11, epsArrayStringI12, epsArrayStringI13, epsArrayStringI14,
            epsArrayStringI15, epsArrayStringI16, epsArrayStringI17, epsArrayStringI18, epsArrayStringI19,
            epsArrayStringI20, epsArrayStringI21, epsArrayStringI22, epsArrayStringI23, epsArrayStringI24,
            epsArrayT01, epsArrayT02, epsArrayT03, epsArrayT04, epsArrayT05, epsArrayT06, epsArrayT07,
            epsArrayT08, epsArrayV01, epsArrayV02, epsArrayV03, epsArrayV04, epsBusV01, epsBusV02, epsBusI01,
            epsBusI02, epsSwState01, epsSwState02, epsSwState03, epsSwState04, epsSwState05, epsSwState06,
            epsSwState07, epsSwState08, epsSwState09, epsSwState10, epsSwState11, epsSwState12, epsSwState13,
            epsSwState14, epsSwState15, epsSwState16, epsSwState17, epsSwState18, epsSwState19, epsSwState20,
            epsSwState21, epsSwState22, epsSwState23, epsSwState24, epsSwI01, epsSwI02, epsSwI03, epsSwI04,
            epsSwI05, epsSwI06, epsSwI07, epsSwI08, epsSwI09, epsSwI10, epsSwI11, epsSwI12, epsSwI13,
            epsSwI14, epsSwI15, epsSwI16, epsSwI17, epsSwI18, epsSwI19, epsSwI20, epsSwI21, epsSwI22,
            epsSwI23, epsSwI24, epsSadaAngle01, epsSadaAngle02, epsSadaRate01, epsSadaRate02, epsPcuT01,
            epsPcuT02, epsLoadShedLevel, epsTotalLoad, epsArrayPower, thmZoneT01, thmZoneT02, thmZoneT03,
            thmZoneT04, thmZoneT05, thmZoneT06, thmZoneT07, thmZoneT08, thmZoneT09, thmZoneT10, thmZoneT11,
            thmZoneT12, thmZoneT13, thmZoneT14, thmZoneT15, thmZoneT16, thmZoneT17, thmZoneT18, thmZoneT19,
            thmZoneT20, thmZoneT21, thmZoneT22, thmZoneT23, thmZoneT24, thmZoneT25, thmZoneT26, thmZoneT27,
            thmZoneT28, thmZoneT29, thmZoneT30, thmZoneT31, thmZoneT32, thmZoneT33, thmZoneT34, thmZoneT35,
            thmZoneT36, thmZoneT37, thmZoneT38, thmZoneT39, thmZoneT40, thmZoneT41, thmZoneT42, thmZoneT43,
            thmZoneT44, thmZoneT45, thmZoneT46, thmZoneT47, thmZoneT48, thmZoneT49, thmZoneT50, thmZoneT51,
            thmZoneT52, thmZoneT53, thmZoneT54, thmZoneT55, thmZoneT56, thmZoneT57, thmZoneT58, thmZoneT59,
            thmZoneT60, thmZoneT61, thmZoneT62, thmZoneT63, thmZoneT64, thmZoneT65, thmZoneT66, thmZoneT67,
            thmZoneT68, thmZoneT69, thmZoneT70, thmZoneT71, thmZoneT72, thmZoneT73, thmZoneT74, thmZoneT75,
            thmZoneT76, thmZoneT77, thmZoneT78, thmZoneT79, thmZoneT80, thmZoneT81, thmZoneT82, thmZoneT83,
            thmZoneT84, thmZoneT85, thmZoneT86, thmZoneT87, thmZoneT88, thmZoneT89, thmZoneT90, thmZoneT91,
            thmZoneT92, thmZoneT93, thmZoneT94, thmZoneT95, thmZoneT96, thmZoneT97, thmZoneT98, thmZoneT99,
            thmZoneT100, thmZoneT101, thmZoneT102, thmZoneT103, thmZoneT104, thmZoneT105, thmZoneT106,
            thmZoneT107, thmZoneT108, thmZoneT109, thmZoneT110, thmZoneT111, thmZoneT112, thmZoneT113,
            thmZoneT114, thmZoneT115, thmZoneT116, thmZoneT117, thmZoneT118, thmZoneT119, thmZoneT120,
            thmZoneT121, thmZoneT122, thmZoneT123, thmZoneT124, thmZoneT125, thmZoneT126, thmZoneT127,
            thmZoneT128, thmZoneT129, thmZoneT130, thmZoneT131, thmZoneT132, thmZoneT133, thmZoneT134,
            thmZoneT135, thmZoneT136, thmZoneT137, thmZoneT138, thmZoneT139, thmZoneT140, thmZoneT141,
            thmZoneT142, thmZoneT143, thmZoneT144, thmZoneT145, thmZoneT146, thmZoneT147, thmZoneT148,
            thmZoneT149, thmZoneT150, thmZoneT151, thmZoneT152, thmZoneT153, thmZoneT154, thmZoneT155,
            thmZoneT156, thmZoneT157, thmZoneT158, thmZoneT159, thmZoneT160, thmZoneT161, thmZoneT162,
            thmZoneT163, thmZoneT164, thmZoneT165, thmZoneT166, thmZoneT167, thmZoneT168, thmZoneT169,
            thmZoneT170, thmZoneT171, thmZoneT172, thmZoneT173, thmZoneT174, thmZoneT175, thmZoneT176,
            thmZoneT177, thmZoneT178, thmZoneT179, thmZoneT180, thmZoneT181, thmZoneT182, thmZoneT183,
            thmZoneT184, thmZoneT185, thmZoneT186, thmZoneT187, thmZoneT188, thmZoneT189, thmZoneT190,
            thmZoneT191, thmZoneT192, thmHtrState01, thmHtrState02, thmHtrState03, thmHtrState04,
            thmHtrState05, thmHtrState06, thmHtrState07, thmHtrState08, thmHtrState09, thmHtrState10,
            thmHtrState11, thmHtrState12, thmHtrState13, thmHtrState14, thmHtrState15, thmHtrState16,
            thmHtrDuty01, thmHtrDuty02, thmHtrDuty03, thmHtrDuty04, thmHtrDuty05, thmHtrDuty06, thmHtrDuty07,
            thmHtrDuty08, thmHtrDuty09, thmHtrDuty10, thmHtrDuty11, thmHtrDuty12, thmHtrDuty13, thmHtrDuty14,
            thmHtrDuty15, thmHtrDuty16, thmHtrI01, thmHtrI02, thmHtrI03, thmHtrI04, thmHtrI05, thmHtrI06,
            thmHtrI07, thmHtrI08, thmHtrI09, thmHtrI10, thmHtrI11, thmHtrI12, thmHtrI13, thmHtrI14,
            thmHtrI15, thmHtrI16, thmSetpoint01, thmSetpoint02, thmSetpoint03, thmSetpoint04, thmSetpoint05,
            thmSetpoint06, thmSetpoint07, thmSetpoint08, thmSetpoint09, thmSetpoint10, thmSetpoint11,
            thmSetpoint12, thmSetpoint13, thmSetpoint14, thmSetpoint15, thmSetpoint16, thmLouverPos01,
            thmLouverPos02, thmLouverPos03, thmLouverPos04, thmHeatPipeT01, thmHeatPipeT02, thmHeatPipeT03,
            thmHeatPipeT04, thmHeatPipeT05, thmHeatPipeT06, thmHeatPipeT07, thmHeatPipeT08, thmRadiatorT01,
            thmRadiatorT02, thmRadiatorT03, thmRadiatorT04, thmHtrPowerTotal, thmControlMode, comTxPower01,
            comTxPower02, comRxAgc01, comRxAgc02, comRxLock01, comRxLock02, comCarrierLock, comSymbolRate,
            comUplinkRate, comFrameCount, comFrameErrors, comSspaT01, comSspaT02, comSspaI01, comSspaI02,
            comHgaAz, comHgaEl, comAntennaSel, comRangingState, comDoppler, comTwoWayRange, comLinkMargin,
            comPassRemaining, comExciterT01, comExciterT02, comXpdrState01, comXpdrState02, comHgaT01,
            comHgaT02, comRelayRxLock, comRelayRate, comRelayFrameCount, comRelayLinkMargin, comCodingSel,
            comHgaMotorI01, comHgaMotorI02, insInspRange, insInspBearing01, insInspBearing02,
            insInspRangeRate, insInspState, insInspBattV, insInspBattSoc, insInspT01, insInspT02, insInspT03,
            insInspT04, insInspT05, insInspT06, insInspT07, insInspT08, insImageCount, insImageQueue,
            insSegmentsRx, insSegmentErrors, insRelayMargin, insCamT01, insCamT02, insCamState01,
            insCamState02, insInspPropellant, insInspThrPulses01, insInspThrPulses02, insInspThrPulses03,
            insInspThrPulses04, insInspThrPulses05, insInspThrPulses06, insInspThrPulses07,
            insInspThrPulses08, insReleaseMechState, insReleaseArmed, insLastContactAge, insImageCompression,
            capBagDeployPos01, capBagDeployPos02, capBagDeployPos03, capBagDeployPos04, capPetalAngle01,
            capPetalAngle02, capPetalAngle03, capPetalAngle04, capPetalMotorI01, capPetalMotorI02,
            capPetalMotorI03, capPetalMotorI04, capPetalT01, capPetalT02, capPetalT03, capPetalT04,
            capCinchTension01, capCinchTension02, capLatchState01, capLatchState02, capLatchState03,
            capLatchState04, capProxRange01, capProxRange02, capProxRange03, capProxRange04, capProxRange05,
            capProxRange06, capProxRange07, capProxRange08, capProxState01, capProxState02, capProxState03,
            capProxState04, capProxState05, capProxState06, capProxState07, capProxState08,
            capBodySpinRate01, capBodySpinRate02, capBodySpinRate03, capDespinTorque, capDespinProgress,
            capCaptureArmed, capCaptureState, capContactForce01, capContactForce02, capContactForce03,
            capBodyMassEst, capApproachRate, capMechanismT01, capMechanismT02, capMechanismT03,
            capMechanismT04, autSeqState01, autSeqState02, autSeqState03, autSeqState04, autSeqStep01,
            autSeqStep02, autSeqStep03, autSeqStep04, autSeqId01, autSeqId02, autSeqId03, autSeqId04,
            autSeqTimeToNext01, autSeqTimeToNext02, autSeqTimeToNext03, autSeqTimeToNext04,
            autRuleFiredCount01, autRuleFiredCount02, autRuleFiredCount03, autRuleFiredCount04,
            autRuleFiredCount05, autRuleFiredCount06, autRuleFiredCount07, autRuleFiredCount08,
            autRuleFiredCount09, autRuleFiredCount10, autRuleFiredCount11, autRuleFiredCount12,
            autRuleFiredCount13, autRuleFiredCount14, autRuleFiredCount15, autRuleFiredCount16,
            autRuleEnabled01, autRuleEnabled02, autRuleEnabled03, autRuleEnabled04, autRuleEnabled05,
            autRuleEnabled06, autRuleEnabled07, autRuleEnabled08, autRuleEnabled09, autRuleEnabled10,
            autRuleEnabled11, autRuleEnabled12, autRuleEnabled13, autRuleEnabled14, autRuleEnabled15,
            autRuleEnabled16, autWaypointIndex, autWaypointRange, autAutonomyLevel, autPlanHorizon,
            autEngineEnabled01, autEngineEnabled02, autEngineEnabled03, autEngineEnabled04, fdrMonState01,
            fdrMonState02, fdrMonState03, fdrMonState04, fdrMonState05, fdrMonState06, fdrMonState07,
            fdrMonState08, fdrMonState09, fdrMonState10, fdrMonState11, fdrMonState12, fdrMonState13,
            fdrMonState14, fdrMonState15, fdrMonState16, fdrMonState17, fdrMonState18, fdrMonState19,
            fdrMonState20, fdrMonState21, fdrMonState22, fdrMonState23, fdrMonState24, fdrMonState25,
            fdrMonState26, fdrMonState27, fdrMonState28, fdrMonState29, fdrMonState30, fdrMonState31,
            fdrMonState32, fdrMonState33, fdrMonState34, fdrMonState35, fdrMonState36, fdrMonState37,
            fdrMonState38, fdrMonState39, fdrMonState40, fdrMonState41, fdrMonState42, fdrMonState43,
            fdrMonState44, fdrMonState45, fdrMonState46, fdrMonState47, fdrMonState48, fdrMonTripCount01,
            fdrMonTripCount02, fdrMonTripCount03, fdrMonTripCount04, fdrMonTripCount05, fdrMonTripCount06,
            fdrMonTripCount07, fdrMonTripCount08, fdrMonTripCount09, fdrMonTripCount10, fdrMonTripCount11,
            fdrMonTripCount12, fdrMonTripCount13, fdrMonTripCount14, fdrMonTripCount15, fdrMonTripCount16,
            fdrMonTripCount17, fdrMonTripCount18, fdrMonTripCount19, fdrMonTripCount20, fdrMonTripCount21,
            fdrMonTripCount22, fdrMonTripCount23, fdrMonTripCount24, fdrMonTripCount25, fdrMonTripCount26,
            fdrMonTripCount27, fdrMonTripCount28, fdrMonTripCount29, fdrMonTripCount30, fdrMonTripCount31,
            fdrMonTripCount32, fdrMonTripCount33, fdrMonTripCount34, fdrMonTripCount35, fdrMonTripCount36,
            fdrMonTripCount37, fdrMonTripCount38, fdrMonTripCount39, fdrMonTripCount40, fdrMonTripCount41,
            fdrMonTripCount42, fdrMonTripCount43, fdrMonTripCount44, fdrMonTripCount45, fdrMonTripCount46,
            fdrMonTripCount47, fdrMonTripCount48, fdrFaultCount, fdrLastFaultId, fdrSafeModeCount,
            fdrCmdLossTimer, fdrResponseMask, fdrFlameoutRetries, fdrResponseState, fdrActiveFaults,
            fdrImpactProbability, fdrEarthRange, modCurrentMode, modPreviousMode, modModeTime,
            modTransitionCount, modPendingMode, modAutoTransitionEn, modModeTableId, modModeTableCrc,
            modSubsystemState01, modSubsystemState02, modSubsystemState03, modSubsystemState04,
            modSubsystemState05, modSubsystemState06, modSubsystemState07, modSubsystemState08,
            modSubsystemState09, modSubsystemState10, modSubsystemState11, modSubsystemState12, modModeHold,
            modTransitionTimeout, pbuTableId01, pbuTableId02, pbuTableId03, pbuTableId04, pbuTableId05,
            pbuTableId06, pbuTableId07, pbuTableId08, pbuTableId09, pbuTableId10, pbuTableId11, pbuTableId12,
            pbuTableCrc01, pbuTableCrc02, pbuTableCrc03, pbuTableCrc04, pbuTableCrc05, pbuTableCrc06,
            pbuTableCrc07, pbuTableCrc08, pbuTableCrc09, pbuTableCrc10, pbuTableCrc11, pbuTableCrc12,
            pbuTableState01, pbuTableState02, pbuTableState03, pbuTableState04, pbuTableState05,
            pbuTableState06, pbuTableState07, pbuTableState08, pbuTableState09, pbuTableState10,
            pbuTableState11, pbuTableState12, pbuBootImageSel, pbuBootImageCrc01, pbuBootImageCrc02,
            pbuUpdateProgress, pbuUpdateState, pbuParamWriteCount, pbuParamRejectCount, pbuEepromWriteCycles);
        :>> events = (
            cdhEvtStarted, cdhEvtStopped, cdhEvtCmdAccepted, cdhEvtCmdRejected, cdhEvtTableLoaded,
            cdhEvtTableInvalid, cdhEvtWatchdogMissed, cdhEvtModeChangeSeen, cdhEvtProcessorReset,
            cdhEvtPrimeSwitched, cdhEvtClockSet, cdhEvtRecorderFull, cdhEvtFileDownlinked,
            cdhEvtMemoryScrubError, gncEvtStarted, gncEvtStopped, gncEvtCmdAccepted, gncEvtCmdRejected,
            gncEvtTableLoaded, gncEvtTableInvalid, gncEvtWatchdogMissed, gncEvtModeChangeSeen,
            gncEvtSlewComplete, gncEvtStarTrackerLost, gncEvtImuFault, gncEvtWheelSaturation,
            gncEvtDesatComplete, gncEvtTcmComplete, gncEvtEstimatorDiverged, gncEvtEphemerisStale,
            sepEvtStarted, sepEvtStopped, sepEvtCmdAccepted, sepEvtCmdRejected, sepEvtTableLoaded,
            sepEvtTableInvalid, sepEvtWatchdogMissed, sepEvtModeChangeSeen, sepEvtArcStarted,
            sepEvtArcComplete, sepEvtFlameout, sepEvtRestartOk, sepEvtRestartFailed, sepEvtTankLow,
            sepEvtPpuOvercurrent, sepEvtGimbalStall, epsEvtStarted, epsEvtStopped, epsEvtCmdAccepted,
            epsEvtCmdRejected, epsEvtTableLoaded, epsEvtTableInvalid, epsEvtWatchdogMissed,
            epsEvtModeChangeSeen, epsEvtLoadShed, epsEvtBatteryLow, epsEvtBusUndervoltage, epsEvtSwitchTrip,
            epsEvtArrayStringLost, epsEvtSadaStall, epsEvtChargeComplete, thmEvtStarted, thmEvtStopped,
            thmEvtCmdAccepted, thmEvtCmdRejected, thmEvtTableLoaded, thmEvtTableInvalid,
            thmEvtWatchdogMissed, thmEvtModeChangeSeen, thmEvtZoneCold, thmEvtZoneHot, thmEvtZoneRed,
            thmEvtHeaterFailed, thmEvtSurvivalActive, thmEvtPowerCapHit, comEvtStarted, comEvtStopped,
            comEvtCmdAccepted, comEvtCmdRejected, comEvtTableLoaded, comEvtTableInvalid,
            comEvtWatchdogMissed, comEvtModeChangeSeen, comEvtCarrierAcquired, comEvtCarrierLost,
            comEvtPassStart, comEvtPassEnd, comEvtTxOvertemp, comEvtHgaPointingError, comEvtRelayAcquired,
            comEvtRelayLost, insEvtStarted, insEvtStopped, insEvtCmdAccepted, insEvtCmdRejected,
            insEvtTableLoaded, insEvtTableInvalid, insEvtWatchdogMissed, insEvtModeChangeSeen,
            insEvtReleaseArmed, insEvtReleased, insEvtImageReceived, insEvtSegmentLost, insEvtInspectorSafe,
            insEvtInspectorRetired, insEvtContactLost, capEvtStarted, capEvtStopped, capEvtCmdAccepted,
            capEvtCmdRejected, capEvtTableLoaded, capEvtTableInvalid, capEvtWatchdogMissed,
            capEvtModeChangeSeen, capEvtCaptureArmed, capEvtBagDeployed, capEvtBagClosed, capEvtContact,
            capEvtContactForceHigh, capEvtDespinComplete, capEvtLatched, capEvtCaptureAborted,
            capEvtPetalStall, capEvtProximitySensorFault, autEvtStarted, autEvtStopped, autEvtCmdAccepted,
            autEvtCmdRejected, autEvtTableLoaded, autEvtTableInvalid, autEvtWatchdogMissed,
            autEvtModeChangeSeen, autEvtSequenceStarted, autEvtSequenceComplete, autEvtSequenceFailed,
            autEvtRuleFired, autEvtWaypointReached, autEvtPlanInfeasible, fdrEvtStarted, fdrEvtStopped,
            fdrEvtCmdAccepted, fdrEvtCmdRejected, fdrEvtTableLoaded, fdrEvtTableInvalid,
            fdrEvtWatchdogMissed, fdrEvtModeChangeSeen, fdrEvtMonitorTrip, fdrEvtResponseTaken,
            fdrEvtSafeModeEntered, fdrEvtCommandLoss, fdrEvtAbortRetreat, fdrEvtFaultCleared,
            fdrEvtImpactProbabilityHigh, fdrEvtExclusionViolation, modEvtStarted, modEvtStopped,
            modEvtCmdAccepted, modEvtCmdRejected, modEvtTableLoaded, modEvtTableInvalid,
            modEvtWatchdogMissed, modEvtModeChangeSeen, modEvtModeEntered, modEvtModePending,
            modEvtModeRejected, modEvtTransitionTimeout, modEvtAutoTransition, pbuEvtStarted, pbuEvtStopped,
            pbuEvtCmdAccepted, pbuEvtCmdRejected, pbuEvtTableLoaded, pbuEvtTableInvalid,
            pbuEvtWatchdogMissed, pbuEvtModeChangeSeen, pbuEvtTableActivated, pbuEvtTableCrcMismatch,
            pbuEvtBootUpdateStarted, pbuEvtBootUpdateComplete, pbuEvtBootFallback, pbuEvtParameterRejected);
        :>> packets = (
            cdhHkPacket01, cdhEngPacket01, cdhEngPacket02, gncHkPacket01, gncEngPacket01, gncEngPacket02,
            gncEngPacket03, sepHkPacket01, sepHkPacket02, sepEngPacket01, sepEngPacket02, epsHkPacket01,
            epsHkPacket02, epsEngPacket01, epsEngPacket02, epsEngPacket03, epsEngPacket04, thmHkPacket01,
            thmEngPacket01, thmEngPacket02, thmEngPacket03, thmEngPacket04, thmEngPacket05, thmEngPacket06,
            thmEngPacket07, thmEngPacket08, thmEngPacket09, thmEngPacket10, thmEngPacket11, comHkPacket01,
            comEngPacket01, insHkPacket01, insEngPacket01, insEngPacket02, capHkPacket01, capHkPacket02,
            capEngPacket01, capEngPacket02, autHkPacket01, autEngPacket01, autEngPacket02, fdrHkPacket01,
            fdrHkPacket02, fdrHkPacket03, fdrEngPacket01, fdrEngPacket02, modHkPacket01, modEngPacket01,
            pbuHkPacket01, pbuHkPacket02, pbuEngPacket01);
        :>> parameterTables = (
            cdhParameterTable, gncParameterTable, sepParameterTable, epsParameterTable, thmParameterTable,
            comParameterTable, insParameterTable, capParameterTable, autParameterTable, fdrParameterTable,
            modParameterTable, pbuParameterTable);
    }
    satisfy dictionaryConsistent by flightDictionary {
        doc /* The flight dictionary passes the dictionary requirement: distinct opcodes, mnemonics, application ids and event ids; every command accepted in at least one mode; every packet summing to its length; every point sourced; every supervisor threshold a table row. */
    }
}
