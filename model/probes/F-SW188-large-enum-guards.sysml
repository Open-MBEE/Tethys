// Probe: a 256-literal enumeration used in `==` transition guards and in a calc, standalone.
// SysML v2 §7.3.4.3 (enumeration definitions) and §7.16.6 (transition guards) put no bound on
// the literal count; the guard `opcode == Op::OP_007` is an ordinary equality (KerML §7.4.9).
// OpenSysML: validates and `-compile`s; the pilot validates it. Timings in docs/findings/WP-SW-2.md.
package F_SW188 {
    private import ScalarValues::*;
    enum def Op {
        OP_000;
        OP_001;
        OP_002;
        OP_003;
        OP_004;
        OP_005;
        OP_006;
        OP_007;
        OP_008;
        OP_009;
        OP_010;
        OP_011;
        OP_012;
        OP_013;
        OP_014;
        OP_015;
        OP_016;
        OP_017;
        OP_018;
        OP_019;
        OP_020;
        OP_021;
        OP_022;
        OP_023;
        OP_024;
        OP_025;
        OP_026;
        OP_027;
        OP_028;
        OP_029;
        OP_030;
        OP_031;
        OP_032;
        OP_033;
        OP_034;
        OP_035;
        OP_036;
        OP_037;
        OP_038;
        OP_039;
        OP_040;
        OP_041;
        OP_042;
        OP_043;
        OP_044;
        OP_045;
        OP_046;
        OP_047;
        OP_048;
        OP_049;
        OP_050;
        OP_051;
        OP_052;
        OP_053;
        OP_054;
        OP_055;
        OP_056;
        OP_057;
        OP_058;
        OP_059;
        OP_060;
        OP_061;
        OP_062;
        OP_063;
        OP_064;
        OP_065;
        OP_066;
        OP_067;
        OP_068;
        OP_069;
        OP_070;
        OP_071;
        OP_072;
        OP_073;
        OP_074;
        OP_075;
        OP_076;
        OP_077;
        OP_078;
        OP_079;
        OP_080;
        OP_081;
        OP_082;
        OP_083;
        OP_084;
        OP_085;
        OP_086;
        OP_087;
        OP_088;
        OP_089;
        OP_090;
        OP_091;
        OP_092;
        OP_093;
        OP_094;
        OP_095;
        OP_096;
        OP_097;
        OP_098;
        OP_099;
        OP_100;
        OP_101;
        OP_102;
        OP_103;
        OP_104;
        OP_105;
        OP_106;
        OP_107;
        OP_108;
        OP_109;
        OP_110;
        OP_111;
        OP_112;
        OP_113;
        OP_114;
        OP_115;
        OP_116;
        OP_117;
        OP_118;
        OP_119;
        OP_120;
        OP_121;
        OP_122;
        OP_123;
        OP_124;
        OP_125;
        OP_126;
        OP_127;
        OP_128;
        OP_129;
        OP_130;
        OP_131;
        OP_132;
        OP_133;
        OP_134;
        OP_135;
        OP_136;
        OP_137;
        OP_138;
        OP_139;
        OP_140;
        OP_141;
        OP_142;
        OP_143;
        OP_144;
        OP_145;
        OP_146;
        OP_147;
        OP_148;
        OP_149;
        OP_150;
        OP_151;
        OP_152;
        OP_153;
        OP_154;
        OP_155;
        OP_156;
        OP_157;
        OP_158;
        OP_159;
        OP_160;
        OP_161;
        OP_162;
        OP_163;
        OP_164;
        OP_165;
        OP_166;
        OP_167;
        OP_168;
        OP_169;
        OP_170;
        OP_171;
        OP_172;
        OP_173;
        OP_174;
        OP_175;
        OP_176;
        OP_177;
        OP_178;
        OP_179;
        OP_180;
        OP_181;
        OP_182;
        OP_183;
        OP_184;
        OP_185;
        OP_186;
        OP_187;
        OP_188;
        OP_189;
        OP_190;
        OP_191;
        OP_192;
        OP_193;
        OP_194;
        OP_195;
        OP_196;
        OP_197;
        OP_198;
        OP_199;
        OP_200;
        OP_201;
        OP_202;
        OP_203;
        OP_204;
        OP_205;
        OP_206;
        OP_207;
        OP_208;
        OP_209;
        OP_210;
        OP_211;
        OP_212;
        OP_213;
        OP_214;
        OP_215;
        OP_216;
        OP_217;
        OP_218;
        OP_219;
        OP_220;
        OP_221;
        OP_222;
        OP_223;
        OP_224;
        OP_225;
        OP_226;
        OP_227;
        OP_228;
        OP_229;
        OP_230;
        OP_231;
        OP_232;
        OP_233;
        OP_234;
        OP_235;
        OP_236;
        OP_237;
        OP_238;
        OP_239;
        OP_240;
        OP_241;
        OP_242;
        OP_243;
        OP_244;
        OP_245;
        OP_246;
        OP_247;
        OP_248;
        OP_249;
        OP_250;
        OP_251;
        OP_252;
        OP_253;
        OP_254;
        OP_255;
    }
    calc def Classify { in op : Op; return r : Natural = if op == Op::OP_000 ? 0 else if op == Op::OP_127 ? 1 else if op == Op::OP_255 ? 2 else 3; }
    attribute c0 : Natural = Classify(op = Op::OP_000);
    attribute c1 : Natural = Classify(op = Op::OP_127);
    attribute c3 : Natural = Classify(op = Op::OP_200);
    part def Processor {
        attribute opcode : Op;
        exhibit state dispatch {
            entry; then idle;
            state idle;
            state resetting;
            state loading;
            state rejected;
            transition idle_reset first idle if opcode == Op::OP_001 then resetting;
            transition idle_load first idle if opcode == Op::OP_128 then loading;
            transition idle_reject first idle if opcode != Op::OP_001 and opcode != Op::OP_128 then rejected;
        }
    }
    part p1 : Processor { :>> opcode = Op::OP_128; }
}
