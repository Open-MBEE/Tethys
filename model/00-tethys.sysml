// Tethys Retrieval: a fictional asteroid-retrieval mission. The mission is invented; the
// physics is not. CONVENTIONS.md governs every file in this directory.
package Tethys {
    doc /* Tethys Retrieval sends the solar-electric tug Argent to the small near-Earth asteroid
         * 2031 QX "Amaranth" (about 7 m across, a few hundred tonnes), characterises it with the
         * free-flying inspector Wren, captures and despins it, and brings it back to a stable
         * lunar distant retrograde orbit where the visiting vehicle Lantern can reach it. It
         * launches on the Arcturus-5H and is operated through the Meridian deep-space network.
         * Every element of the mission — stakeholders, requirements, architecture, budgets,
         * behaviour, analyses, verification, risks, the as-built individual and its operations —
         * lives in the sibling packages of this model. */
}
